-- COPYRIGHT NOTICE
-- Copyright (c) Radware Ltd. 2009
-- All rights reserved

ALTEON-CHEETAH-NETWORK-MIB DEFINITIONS ::= BEGIN

IMPORTS
    MODULE-IDENTITY, OBJECT-TYPE, Integer32, Counter32, Gauge32,
    IpAddress, Unsigned32
        FROM SNMPv2-SMI
    DisplayString, PhysAddress
        FROM SNMPv2-TC
    aws-switch
        FROM ALTEON-ROOT-MIB;

layer3 MODULE-IDENTITY
    LAST-UPDATED "200908050000Z"     -- 5 August, 2009
    ORGANIZATION "Radware Ltd."
    CONTACT-INFO "Lobby 1 (Visitors) and Lobby 2 (Deliveries)
                  575 Corporate Drive
                  Mahwah, NJ 07430
  	     	  support@radware.com"
    DESCRIPTION
        "The MIB module for the Alteon OS Layer 3 configuration, statistics
         and information ."
    REVISION "200908050000Z"     -- 5 August, 2009
    DESCRIPTION
        "Added revision clause for SMIv2 compliance."
    ::= { aws-switch 3 }
layer3Configs     OBJECT IDENTIFIER ::= { layer3 1 }
layer3Stats       OBJECT IDENTIFIER ::= { layer3 2 }
layer3Info        OBJECT IDENTIFIER ::= { layer3 3 }
layer3Oper        OBJECT IDENTIFIER ::= { layer3 4 }

ipInterfaceCfg	    OBJECT IDENTIFIER ::= { layer3Configs 1 }
ipGatewayCfg	    OBJECT IDENTIFIER ::= { layer3Configs 2 }
ipStaticRouteCfg    OBJECT IDENTIFIER ::= { layer3Configs 3 }
ipForwardCfg	    OBJECT IDENTIFIER ::= { layer3Configs 4 }
vrrpCfg		    OBJECT IDENTIFIER ::= { layer3Configs 6 }
arpCfg		    OBJECT IDENTIFIER ::= { layer3Configs 7 }
ipBootpCfg	    OBJECT IDENTIFIER ::= { layer3Configs 8 }
dnsCfg  	    OBJECT IDENTIFIER ::= { layer3Configs 9 }
ipNwfCfg	    OBJECT IDENTIFIER ::= { layer3Configs 10 }
ipRmapCfg	    OBJECT IDENTIFIER ::= { layer3Configs 11 }
bgpCfg		    OBJECT IDENTIFIER ::= { layer3Configs 12 }
ospfCfg		    OBJECT IDENTIFIER ::= { layer3Configs 13 }
ipGeneralCfg	    OBJECT IDENTIFIER ::= { layer3Configs 14 }
ipStaticArpCfg      OBJECT IDENTIFIER ::= { layer3Configs 15 }
rip2Cfg		    OBJECT IDENTIFIER ::= { layer3Configs 18 }

arpStats  	  OBJECT IDENTIFIER ::= { layer3Stats 2 }
routeStats  	  OBJECT IDENTIFIER ::= { layer3Stats 3 }
dnsStats  	  OBJECT IDENTIFIER ::= { layer3Stats 4 }
vrrpStats         OBJECT IDENTIFIER ::= { layer3Stats 5 }
ospfStats	  OBJECT IDENTIFIER ::= { layer3Stats 6 }
clearStats	  OBJECT IDENTIFIER ::= { layer3Stats 7 }
ip6Stats          OBJECT IDENTIFIER ::= { layer3Stats 10}
icmp6Stats        OBJECT IDENTIFIER ::= { layer3Stats 11}
ip6gwStats        OBJECT IDENTIFIER ::= { layer3Stats 12}
rip2Stats  	  OBJECT IDENTIFIER ::= { layer3Stats 13 }
tcpStats  	  OBJECT IDENTIFIER ::= { layer3Stats 14 }

ipRoutingInfo	  OBJECT IDENTIFIER ::= { layer3Info 1 }
arpInfo		  OBJECT IDENTIFIER ::= { layer3Info 2 }
vrrpInfo	  OBJECT IDENTIFIER ::= { layer3Info 3 }
ospfinfo	  OBJECT IDENTIFIER ::= { layer3Info 4 }
gatewayInfo	  OBJECT IDENTIFIER ::= { layer3Info 5 }
nbrcacheInfo      OBJECT IDENTIFIER ::= { layer3Info 7 }
ipRoute6Info      OBJECT IDENTIFIER ::= { layer3Info 8 }
ipIntfInfo        OBJECT IDENTIFIER ::= { layer3Info 9 }
rip2Info          OBJECT IDENTIFIER ::= { layer3Info 10 }

rip2RoutesInfo    OBJECT IDENTIFIER ::= { layer3Info 11 }
allowedNwInfo     OBJECT IDENTIFIER ::= { layer3Info 12 }

vrrpOper          OBJECT IDENTIFIER ::= { layer3Oper 1 }

ipOper            OBJECT IDENTIFIER ::= { layer3Oper 2 }

-- IP Configuration

ipInterfaceTableMax OBJECT-TYPE
    SYNTAX  Integer32
    MAX-ACCESS  read-only
    STATUS  current
    DESCRIPTION
        "The maximum number of rows in the IP interface table."
    ::= { ipInterfaceCfg 1 }

ipCurCfgIntfTable OBJECT-TYPE
    SYNTAX  SEQUENCE OF IpCurCfgIntfEntry
    MAX-ACCESS  not-accessible
    STATUS  current
    DESCRIPTION
        "The table of IP interface configuration."
    ::= { ipInterfaceCfg 2 }

ipCurCfgIntfEntry OBJECT-TYPE
    SYNTAX  IpCurCfgIntfEntry
    MAX-ACCESS  not-accessible
    STATUS  current
    DESCRIPTION
        "A row in the Ip interface table"
    INDEX   { ipCurCfgIntfIndex }
    ::= { ipCurCfgIntfTable 1 }

IpCurCfgIntfEntry ::= SEQUENCE {
    ipCurCfgIntfIndex         Integer32,
    ipCurCfgIntfAddr          IpAddress,
    ipCurCfgIntfMask          IpAddress,
    ipCurCfgIntfBroadcast     IpAddress,
    ipCurCfgIntfState         INTEGER,
    ipCurCfgIntfBootpRelay    INTEGER,
    ipCurCfgIntfIpVer         INTEGER,
    ipCurCfgIntfIpv6Addr      DisplayString,
    ipCurCfgIntfPrefixLen     INTEGER,
    ipCurCfgIntfRouteAdv      INTEGER,
    ipCurCfgIntfVlan          Integer32
    }

ipCurCfgIntfIndex OBJECT-TYPE
    SYNTAX  Integer32
    MAX-ACCESS  read-only
    STATUS  current
    DESCRIPTION
        "The interface number for which the IP information is related."
    ::= { ipCurCfgIntfEntry 1}

ipCurCfgIntfAddr OBJECT-TYPE
    SYNTAX  IpAddress
    MAX-ACCESS  read-only
    STATUS  current
    DESCRIPTION
        "The IP address of the interface."
    ::= { ipCurCfgIntfEntry 2 }

ipCurCfgIntfMask OBJECT-TYPE
    SYNTAX  IpAddress
    MAX-ACCESS  read-only
    STATUS  current
    DESCRIPTION
        "The subnet mask of the interface."
    ::= { ipCurCfgIntfEntry 3 }

ipCurCfgIntfBroadcast OBJECT-TYPE
    SYNTAX  IpAddress
    MAX-ACCESS  read-only
    STATUS  obsolete
    DESCRIPTION
        "The broadcast address of the interface."
    ::= { ipCurCfgIntfEntry 4 }

ipCurCfgIntfVlan OBJECT-TYPE
    SYNTAX  Integer32
    MAX-ACCESS  read-only
    STATUS  current
    DESCRIPTION
        "The VLAN associated with the interface."
    ::= { ipCurCfgIntfEntry 5 }

ipCurCfgIntfState OBJECT-TYPE
    SYNTAX  INTEGER {
	enabled(2),
	disabled(3)
	}
    MAX-ACCESS  read-only
    STATUS  current
    DESCRIPTION
        "The state of the interface."
    ::= { ipCurCfgIntfEntry 6 }

ipCurCfgIntfBootpRelay OBJECT-TYPE
    SYNTAX  INTEGER {
	enabled(1),
	disabled(2)
	}
    MAX-ACCESS  read-only
    STATUS  current
    DESCRIPTION
        "Enable/disable BOOTP relay."
    ::= { ipCurCfgIntfEntry 7 }



ipCurCfgIntfIpVer OBJECT-TYPE
    SYNTAX  INTEGER{
        ipv4(1),
        ipv6(2)
        }
    MAX-ACCESS  read-only
    STATUS  current
    DESCRIPTION
        "The type of IP address."
    ::= { ipCurCfgIntfEntry 9 }

ipCurCfgIntfIpv6Addr OBJECT-TYPE
    SYNTAX   DisplayString (SIZE(0..40))
    MAX-ACCESS  read-only
    STATUS  current
    DESCRIPTION
        "The IPv6 address of the interface. Address should be 4-byte
         haxadecimal colon notation.
         Valid IPv6 address should be in any of the following forms
           xxxx:xxxx:xxxx:xxxx:xxxx:xxxx:xxxx:xxxx or
           xxxx::xxxx:xxxx:xxxx:xxxx or ::xxxx"
    ::= { ipCurCfgIntfEntry 10 }

ipCurCfgIntfPrefixLen OBJECT-TYPE
    SYNTAX  INTEGER(1..128)
    MAX-ACCESS  read-only
    STATUS  current
    DESCRIPTION
        "The prefix length associated with this IP address ."
    ::= { ipCurCfgIntfEntry 11 }

ipCurCfgIntfRouteAdv  OBJECT-TYPE
    SYNTAX  INTEGER {
        enabled(1),
        disabled(2)
        }
    MAX-ACCESS  read-only
    STATUS  current
    DESCRIPTION
        "Enable/disable route advertisement of the interface."
    ::= { ipCurCfgIntfEntry 12 }


ipNewCfgIntfTable OBJECT-TYPE
    SYNTAX  SEQUENCE OF IpNewCfgIntfEntry
    MAX-ACCESS  not-accessible
    STATUS  current
    DESCRIPTION
        "The table of interface configuration in the New Configuration Block."
    ::= { ipInterfaceCfg 3 }

ipNewCfgIntfEntry OBJECT-TYPE
    SYNTAX  IpNewCfgIntfEntry
    MAX-ACCESS  not-accessible
    STATUS  current
    DESCRIPTION
        "A row in the Ip interface table"
    INDEX   { ipNewCfgIntfIndex }
    ::= { ipNewCfgIntfTable 1 }

IpNewCfgIntfEntry ::= SEQUENCE {
    ipNewCfgIntfIndex         Integer32,
    ipNewCfgIntfAddr          IpAddress,
    ipNewCfgIntfMask          IpAddress,
    ipNewCfgIntfBroadcast     IpAddress,
    ipNewCfgIntfVlan          Integer32,
    ipNewCfgIntfState         INTEGER,
    ipNewCfgIntfBootpRelay    INTEGER,
    ipNewCfgIntfIpVer         INTEGER,
    ipNewCfgIntfIpv6Addr      DisplayString,
    ipNewCfgIntfPrefixLen     INTEGER,
    ipNewCfgIntfRouteAdv      INTEGER,
    ipNewCfgIntfDelete	      INTEGER
    }

ipNewCfgIntfIndex OBJECT-TYPE
    SYNTAX  Integer32
    MAX-ACCESS  read-only
    STATUS  current
    DESCRIPTION
	"The interface number for which the IP information is related."
    ::= { ipNewCfgIntfEntry 1 }

ipNewCfgIntfAddr OBJECT-TYPE
    SYNTAX  IpAddress
    MAX-ACCESS  read-create
    STATUS  current
    DESCRIPTION
        "The IP address of the interface."
    ::= { ipNewCfgIntfEntry 2 }

ipNewCfgIntfMask OBJECT-TYPE
    SYNTAX  IpAddress
    MAX-ACCESS  read-create
    STATUS  current
    DESCRIPTION
        "The subnet mask of the interface."
    ::= { ipNewCfgIntfEntry 3 }

ipNewCfgIntfBroadcast OBJECT-TYPE
    SYNTAX  IpAddress
    MAX-ACCESS  read-create
    STATUS  obsolete
    DESCRIPTION
        "The broadcast address of the interface."
    ::= { ipNewCfgIntfEntry 4 }

ipNewCfgIntfVlan OBJECT-TYPE
    SYNTAX  Integer32
    MAX-ACCESS  read-create
    STATUS  current
    DESCRIPTION
        "The VLAN associated with the interface."
    ::= { ipNewCfgIntfEntry 5 }

ipNewCfgIntfState OBJECT-TYPE
    SYNTAX  INTEGER {
	enabled(2),
	disabled(3)
	}
    MAX-ACCESS  read-create
    STATUS  current
    DESCRIPTION
        "The state of the interface."
    ::= { ipNewCfgIntfEntry 6 }

ipNewCfgIntfDelete OBJECT-TYPE
    SYNTAX  INTEGER {
	other(1),
        delete(2)
	}
    MAX-ACCESS  read-create
    STATUS  current
    DESCRIPTION
        "When set to the value of 2 (delete), the entire row is deleted.
         When read, other(1) is returned. Setting the value to anything
         other than 2(delete) has no effect on the state of the row."
    ::= { ipNewCfgIntfEntry 7 }

ipNewCfgIntfBootpRelay OBJECT-TYPE
    SYNTAX  INTEGER {
	enabled(1),
	disabled(2)
	}
    MAX-ACCESS  read-create
    STATUS  current
    DESCRIPTION
        "Enable/disable BOOTP relay."
    ::= { ipNewCfgIntfEntry 8 }


ipNewCfgIntfIpVer OBJECT-TYPE
    SYNTAX  INTEGER{
        ipv4(1),
        ipv6(2)
        }
    MAX-ACCESS read-create
    STATUS  current
    DESCRIPTION
        "The type of IP address."
    ::= { ipNewCfgIntfEntry 10 }

ipNewCfgIntfIpv6Addr OBJECT-TYPE
    SYNTAX  DisplayString  (SIZE(0..40))
    MAX-ACCESS read-create
    STATUS  current
    DESCRIPTION
        "The IPv6 address of the interface. Address should be 4-byte
         haxadecimal colon notation.
         Valid IPv6 address should be in any of the following forms
           xxxx:xxxx:xxxx:xxxx:xxxx:xxxx:xxxx:xxxx or
           xxxx::xxxx:xxxx:xxxx:xxxx or ::xxxx"
    ::= { ipNewCfgIntfEntry 11 }

ipNewCfgIntfPrefixLen OBJECT-TYPE
    SYNTAX  INTEGER (1..128)
    MAX-ACCESS read-create
    STATUS  current
    DESCRIPTION
        "The prefix length associated with this IP address ."
    ::= { ipNewCfgIntfEntry 12 }

ipNewCfgIntfRouteAdv  OBJECT-TYPE
    SYNTAX  INTEGER {
        enabled(1),
        disabled(2)
        }
    MAX-ACCESS  read-create
    STATUS  current
    DESCRIPTION
        "Enable/disable route advertisement of the interface."
    ::= { ipNewCfgIntfEntry 13 }


-- IP Gateway Table Configuration

ipCurCfgGwMetric OBJECT-TYPE
    SYNTAX  INTEGER {
        strict(1),
        roundrobin(2)
        }
    MAX-ACCESS  read-only
    STATUS  current
    DESCRIPTION
        "The default gateway metric."
    ::= { ipGatewayCfg 1 }

ipNewCfgGwMetric OBJECT-TYPE
    SYNTAX  INTEGER {
        strict(1),
        roundrobin(2)
        }
    MAX-ACCESS  read-write
    STATUS  current
    DESCRIPTION
        "The default gateway metric."
    ::= { ipGatewayCfg 2 }

ipGatewayTableMax OBJECT-TYPE
    SYNTAX  Integer32
    MAX-ACCESS  read-only
    STATUS  current
    DESCRIPTION
        "The maximum number of rows in the IP gateway table."
    ::= { ipGatewayCfg 3 }

ipCurCfgGwTable OBJECT-TYPE
    SYNTAX  SEQUENCE OF IpCurCfgGwEntry
    MAX-ACCESS  not-accessible
    STATUS  current
    DESCRIPTION
        "The table of gateways  in the Current configuration Block."
    ::= { ipGatewayCfg 4 }

ipCurCfgGwEntry OBJECT-TYPE
    SYNTAX  IpCurCfgGwEntry
    MAX-ACCESS  not-accessible
    STATUS  current
    DESCRIPTION
        "A row in the Ip gateway table"
    INDEX   { ipCurCfgGwIndex }
    ::= { ipCurCfgGwTable 1 }

IpCurCfgGwEntry ::= SEQUENCE {
    ipCurCfgGwIndex         Integer32,
    ipCurCfgGwAddr          IpAddress,
    ipCurCfgGwInterval      INTEGER,
    ipCurCfgGwRetry         INTEGER,
    ipCurCfgGwArp           INTEGER,
    ipCurCfgGwVlan          Integer32,
    ipCurCfgGwIpVer         INTEGER,
    ipCurCfgGwIpv6Addr      DisplayString,
    ipCurCfgGwPriority      INTEGER,
    ipCurCfgGwState         INTEGER
    }

ipCurCfgGwIndex OBJECT-TYPE
    SYNTAX  Integer32
    MAX-ACCESS  read-only
    STATUS  current
    DESCRIPTION
        "The gateway number for which the information is related."
    ::= { ipCurCfgGwEntry 1}

ipCurCfgGwAddr OBJECT-TYPE
    SYNTAX  IpAddress
    MAX-ACCESS  read-only
    STATUS  current
    DESCRIPTION
        "The IP address of the default gateway."
    ::= { ipCurCfgGwEntry 2 }

ipCurCfgGwInterval OBJECT-TYPE
    SYNTAX  INTEGER (0..60)
    MAX-ACCESS  read-only
    STATUS  current
    DESCRIPTION
        "The interval between ping attempts."
    ::= { ipCurCfgGwEntry 3 }

ipCurCfgGwRetry OBJECT-TYPE
    SYNTAX  INTEGER (1..120)
    MAX-ACCESS  read-only
    STATUS  current
    DESCRIPTION
        "The number of failed attempts to declare the default gateway DOWN."
    ::= { ipCurCfgGwEntry 4 }

ipCurCfgGwState OBJECT-TYPE
    SYNTAX  INTEGER {
        enabled(2),
        disabled(3)
	}
    MAX-ACCESS  read-only
    STATUS  current
    DESCRIPTION
        "The state of the default gateway."
    ::= { ipCurCfgGwEntry 5 }

ipCurCfgGwArp OBJECT-TYPE
    SYNTAX  INTEGER {
        enabled(2),
        disabled(3)
        }
    MAX-ACCESS  read-only
    STATUS  current
    DESCRIPTION
        "The state of ARP only health checks."
    ::= { ipCurCfgGwEntry 6 }

ipCurCfgGwVlan OBJECT-TYPE
    SYNTAX  Integer32
    MAX-ACCESS  read-only
    STATUS  current
    DESCRIPTION
        "The VLAN number for this gateway. The first 4 entries in the table
         are only used for default gateway load balancing hence the VLAN
         cannot be specified for the first 4 entries."
    ::= { ipCurCfgGwEntry 7 }

ipCurCfgGwPriority OBJECT-TYPE
    SYNTAX  INTEGER {
	low(1),
	high(2)
	}
    MAX-ACCESS  read-only
    STATUS  current
    DESCRIPTION
        "The priority of the default route for this gateway. High priority
	 means that the default gateway route will have higher priority
	 over learned default routes.  Low priority means that the default
	 gateway route will have lower priority than learned default
	 routes."
    ::= { ipCurCfgGwEntry 8 }

ipCurCfgGwIpVer OBJECT-TYPE
    SYNTAX  INTEGER{
        ipv4(1),
        ipv6(2)
        }
    MAX-ACCESS  read-only
    STATUS  current
    DESCRIPTION
        "The type of IP address."
   ::= { ipCurCfgGwEntry 9 }

ipCurCfgGwIpv6Addr OBJECT-TYPE
    SYNTAX   DisplayString (SIZE(0..40))
    MAX-ACCESS  read-only
    STATUS  current
    DESCRIPTION
        "The IPv6 address of the gateway. Address should be 4-byte
         haxadecimal colon notation.
         Valid IPv6 address should be in any of the following forms
           xxxx:xxxx:xxxx:xxxx:xxxx:xxxx:xxxx:xxxx or
           xxxx::xxxx:xxxx:xxxx:xxxx or ::xxxx"
    ::= { ipCurCfgGwEntry 10 }


ipNewCfgGwTable OBJECT-TYPE
    SYNTAX  SEQUENCE OF IpNewCfgGwEntry
    MAX-ACCESS  not-accessible
    STATUS  current
    DESCRIPTION
        "The table of gateway configuration in the new configuration block."
    ::= { ipGatewayCfg 5 }

ipNewCfgGwEntry OBJECT-TYPE
    SYNTAX  IpNewCfgGwEntry
    MAX-ACCESS  not-accessible
    STATUS  current
    DESCRIPTION
        "A row in the Ip default gateway table"
    INDEX   { ipNewCfgGwIndex }
    ::= { ipNewCfgGwTable 1 }

IpNewCfgGwEntry ::= SEQUENCE {
    ipNewCfgGwIndex         Integer32,
    ipNewCfgGwAddr          IpAddress,
    ipNewCfgGwInterval      INTEGER,
    ipNewCfgGwRetry         INTEGER,
    ipNewCfgGwState         INTEGER,
    ipNewCfgGwArp           INTEGER,
    ipNewCfgGwVlan          Integer32,
    ipNewCfgGwIpVer         INTEGER,
    ipNewCfgGwIpv6Addr      DisplayString,
    ipNewCfgGwPriority      INTEGER,
    ipNewCfgGwDelete        INTEGER
    }

ipNewCfgGwIndex OBJECT-TYPE
    SYNTAX  Integer32
    MAX-ACCESS  read-only
    STATUS  current
    DESCRIPTION
        "The gateway number for which the information is related."
    ::= { ipNewCfgGwEntry 1}

ipNewCfgGwAddr OBJECT-TYPE
    SYNTAX  IpAddress
    MAX-ACCESS  read-create
    STATUS  current
    DESCRIPTION
        "The IP address of the default gateway."
    ::= { ipNewCfgGwEntry 2 }

ipNewCfgGwInterval OBJECT-TYPE
    SYNTAX  INTEGER (0..60)
    MAX-ACCESS  read-create
    STATUS  current
    DESCRIPTION
        "The interval in seconds between ping attempts."
    ::= { ipNewCfgGwEntry 3 }

ipNewCfgGwRetry OBJECT-TYPE
    SYNTAX  INTEGER (1..120)
    MAX-ACCESS  read-create
    STATUS  current
    DESCRIPTION
        "The number of failed attempts to declare the default gateway DOWN."
    ::= { ipNewCfgGwEntry 4 }

ipNewCfgGwState OBJECT-TYPE
    SYNTAX  INTEGER {
        enabled(2),
        disabled(3)
	}
    MAX-ACCESS  read-create
    STATUS  current
    DESCRIPTION
        "The state of the default gateway."
    ::= { ipNewCfgGwEntry 5 }

ipNewCfgGwDelete OBJECT-TYPE
    SYNTAX  INTEGER {
	other(1),
        delete(2)
        }
    MAX-ACCESS  read-create
    STATUS  current
    DESCRIPTION
        "When set to the value of 2 (delete), the entire row is deleted.
         When read, other is returned. Setting the value to anything other
         than 2(delete) has no effect on the state of the row."
    ::= { ipNewCfgGwEntry 6 }

ipNewCfgGwArp OBJECT-TYPE
    SYNTAX  INTEGER {
        enabled(2),
        disabled(3)
        }
    MAX-ACCESS  read-create
    STATUS  current
    DESCRIPTION
        "The state of the ARP only health checks."
    ::= { ipNewCfgGwEntry 7 }

ipNewCfgGwVlan OBJECT-TYPE
    SYNTAX  Integer32
    MAX-ACCESS  read-create
    STATUS  current
    DESCRIPTION
        "The VLAN number for this gateway. The first 4 entries in the table
         are only used for default gateway load balancing hence the VLAN
         cannot be specified for the first 4 entries."
    ::= { ipNewCfgGwEntry 8 }

ipNewCfgGwPriority OBJECT-TYPE
    SYNTAX  INTEGER {
	low(1),
	high(2)
	}
    MAX-ACCESS  read-create
    STATUS  current
    DESCRIPTION
        "The priority of the default route for this gateway. High priority
	 means that the default gateway route will have higher priority
	 over learned default routes.  Low priority means that the default
	 gateway route will have lower priority than learned default
	 routes."
    ::= { ipNewCfgGwEntry 9 }


ipNewCfgGwIpVer OBJECT-TYPE
    SYNTAX  INTEGER{
        ipv4(1),
        ipv6(2)
        }
    MAX-ACCESS read-create
    STATUS  current
    DESCRIPTION
        "The type of IP address."
    ::= { ipNewCfgGwEntry 10 }

ipNewCfgGwIpv6Addr OBJECT-TYPE
    SYNTAX  DisplayString  (SIZE(0..40))
    MAX-ACCESS read-create
    STATUS  current
    DESCRIPTION
        "The IPv6 address of the gateway. Address should be 4-byte
         haxadecimal colon notation.
         Valid IPv6 address should be in any of the following forms
           xxxx:xxxx:xxxx:xxxx:xxxx:xxxx:xxxx:xxxx or
           xxxx::xxxx:xxxx:xxxx:xxxx or ::xxxx"
    ::= { ipNewCfgGwEntry 11 }


--
-- IP Static Route Configuration
--
ipStaticRouteTableMaxSize OBJECT-TYPE
    SYNTAX  Integer32
    MAX-ACCESS  read-only
    STATUS  current
    DESCRIPTION
        "The maximum number of rows in the Static Route table."
    ::= { ipStaticRouteCfg 1 }

ipCurCfgStaticRouteTable OBJECT-TYPE
    SYNTAX  SEQUENCE OF IpCurCfgStaticRouteEntry
    MAX-ACCESS  not-accessible
    STATUS  current
    DESCRIPTION
        "The table of static routes in the current configuration block."
    ::= { ipStaticRouteCfg 2 }

ipCurCfgStaticRouteEntry OBJECT-TYPE
    SYNTAX  IpCurCfgStaticRouteEntry
    MAX-ACCESS  not-accessible
    STATUS  current
    DESCRIPTION
        "A row in the static IP route table"
    INDEX   { ipCurCfgStaticRouteIndx }
    ::= { ipCurCfgStaticRouteTable 1 }

IpCurCfgStaticRouteEntry ::= SEQUENCE {
    ipCurCfgStaticRouteIndx         Integer32,
    ipCurCfgStaticRouteDestIp       IpAddress,
    ipCurCfgStaticRouteMask         IpAddress,
    ipCurCfgStaticRouteGateway      IpAddress,
    ipCurCfgStaticRouteInterface    Integer32
    }

ipCurCfgStaticRouteIndx OBJECT-TYPE
    SYNTAX  Integer32
    MAX-ACCESS  read-only
    STATUS  current
    DESCRIPTION
        "The index of the static routing table."
    ::= { ipCurCfgStaticRouteEntry 1}

ipCurCfgStaticRouteDestIp OBJECT-TYPE
    SYNTAX  IpAddress
    MAX-ACCESS  read-only
    STATUS  current
    DESCRIPTION
        "The destination IP address of this route."
    ::= { ipCurCfgStaticRouteEntry 2}

ipCurCfgStaticRouteMask OBJECT-TYPE
    SYNTAX  IpAddress
    MAX-ACCESS  read-only
    STATUS  current
    DESCRIPTION
        "The destination IP address of this route."
    ::= { ipCurCfgStaticRouteEntry 3}

ipCurCfgStaticRouteGateway OBJECT-TYPE
    SYNTAX  IpAddress
    MAX-ACCESS  read-only
    STATUS  current
    DESCRIPTION
        "The destination IP address of this route."
    ::= { ipCurCfgStaticRouteEntry 4}

ipCurCfgStaticRouteInterface OBJECT-TYPE
    SYNTAX  Integer32
    MAX-ACCESS  read-only
    STATUS  current
    DESCRIPTION
        "The IP interface of this route.  The IP address of the specified
         interface shall be use as source IP when performs routing."
    ::= { ipCurCfgStaticRouteEntry 5}

ipNewCfgStaticRouteTable OBJECT-TYPE
    SYNTAX  SEQUENCE OF IpNewCfgStaticRouteEntry
    MAX-ACCESS  not-accessible
    STATUS  current
    DESCRIPTION
        "The table of static routes in the new configuration block."
    ::= { ipStaticRouteCfg 3 }

ipNewCfgStaticRouteEntry OBJECT-TYPE
    SYNTAX  IpNewCfgStaticRouteEntry
    MAX-ACCESS  not-accessible
    STATUS  current
    DESCRIPTION
        "A row in the static IP route table"
    INDEX   { ipNewCfgStaticRouteIndx }
    ::= { ipNewCfgStaticRouteTable 1 }

IpNewCfgStaticRouteEntry ::= SEQUENCE {
    ipNewCfgStaticRouteIndx         Integer32,
    ipNewCfgStaticRouteDestIp       IpAddress,
    ipNewCfgStaticRouteMask         IpAddress,
    ipNewCfgStaticRouteGateway      IpAddress,
    ipNewCfgStaticRouteAction       INTEGER,
    ipNewCfgStaticRouteInterface    Integer32
    }

ipNewCfgStaticRouteIndx OBJECT-TYPE
    SYNTAX  Integer32
    MAX-ACCESS  read-only
    STATUS  current
    DESCRIPTION
        "The index of the static routing table."
    ::= { ipNewCfgStaticRouteEntry 1}

ipNewCfgStaticRouteDestIp OBJECT-TYPE
    SYNTAX  IpAddress
    MAX-ACCESS  read-create
    STATUS  current
    DESCRIPTION
        "The destination IP address of this route."
    ::= { ipNewCfgStaticRouteEntry 2}

ipNewCfgStaticRouteMask OBJECT-TYPE
    SYNTAX  IpAddress
    MAX-ACCESS  read-create
    STATUS  current
    DESCRIPTION
        "The subnet mask of this route."
    ::= { ipNewCfgStaticRouteEntry 3}

ipNewCfgStaticRouteGateway OBJECT-TYPE
    SYNTAX  IpAddress
    MAX-ACCESS  read-create
    STATUS  current
    DESCRIPTION
        "The IP address of the gateway for this route."
    ::= { ipNewCfgStaticRouteEntry 4}

ipNewCfgStaticRouteAction OBJECT-TYPE
    SYNTAX  INTEGER {
        other(1),
        delete(2)
       }
    MAX-ACCESS  read-create
    STATUS  current
    DESCRIPTION
        "When set to the value of 2 (delete), the entire row is deleted.
         When read, other is returned. Setting the value to anything other
         than 2(delete) has no effect on the state of the row."
    ::= { ipNewCfgStaticRouteEntry 5 }

ipNewCfgStaticRouteInterface OBJECT-TYPE
    SYNTAX  Integer32
    MAX-ACCESS  read-create
    STATUS  current
    DESCRIPTION
        "The IP interface of this route.  The IP address of the specified
         interface shall be use as source IP when performs routing."
    ::= { ipNewCfgStaticRouteEntry 6 }

-- IPV6 static routes
ipv6CurCfgStaticRouteTable OBJECT-TYPE
    SYNTAX  SEQUENCE OF Ipv6CurCfgStaticRouteEntry
    MAX-ACCESS  not-accessible
    STATUS  current
    DESCRIPTION
        "The table of ipv6 static routes in the current configuration block."
    ::= { ipStaticRouteCfg 4 }

ipv6CurCfgStaticRouteEntry OBJECT-TYPE
    SYNTAX  Ipv6CurCfgStaticRouteEntry
    MAX-ACCESS  not-accessible
    STATUS  current
    DESCRIPTION
        "A row in the static IP route table"
    INDEX   { ipv6CurCfgStaticRouteIndx }
    ::= { ipv6CurCfgStaticRouteTable 1 }

Ipv6CurCfgStaticRouteEntry ::= SEQUENCE {
    ipv6CurCfgStaticRouteIndx         Integer32,
    ipv6CurCfgStaticRouteDestIp       DisplayString,
    ipv6CurCfgStaticRouteMask         Integer32,
    ipv6CurCfgStaticRouteGateway      DisplayString,
    ipv6CurCfgStaticRouteInterface    Integer32
    }


ipv6CurCfgStaticRouteIndx OBJECT-TYPE
    SYNTAX  Integer32
    MAX-ACCESS  read-only
    STATUS  current
    DESCRIPTION
        "The index of the ipv6 static routing table."
    ::= { ipv6CurCfgStaticRouteEntry 1}

ipv6CurCfgStaticRouteDestIp OBJECT-TYPE
    SYNTAX  DisplayString (SIZE(0..40))
    MAX-ACCESS  read-only
    STATUS  current
    DESCRIPTION
        " The destination IPv6 address of this route.
          Address should be 4-byte haxadecimal colon notation. Valid IPv6 address should be in
          any of the following forms xxxx:xxxx:xxxx:xxxx:xxxx:xxxx:xxxx:xxxx or xxxx::xxxx:xxxx:xxxx:xxxx or ::xxxx"
    ::= { ipv6CurCfgStaticRouteEntry 2}

ipv6CurCfgStaticRouteMask OBJECT-TYPE
    SYNTAX  Integer32 (1..128)
    MAX-ACCESS  read-only
    STATUS  current
    DESCRIPTION
        "The prefix length associated with this IP address."
    ::= { ipv6CurCfgStaticRouteEntry 3}

ipv6CurCfgStaticRouteGateway OBJECT-TYPE
    SYNTAX  DisplayString (SIZE(0..40))
    MAX-ACCESS  read-only
    STATUS  current
    DESCRIPTION
        "The destination IPv6 gateway address of this route.
          Address should be 4-byte haxadecimal colon notation. Valid IPv6 address should be in
          any of the following forms xxxx:xxxx:xxxx:xxxx:xxxx:xxxx:xxxx:xxxx or xxxx::xxxx:xxxx:xxxx:xxxx or ::xxxx"
    ::= { ipv6CurCfgStaticRouteEntry 4}

ipv6CurCfgStaticRouteInterface OBJECT-TYPE
    SYNTAX  Integer32 (1..256)
    MAX-ACCESS  read-only
    STATUS  current
    DESCRIPTION
        "The IPv6 interface of this route.  The IPv6 address of the specified
         interface shall be use as source IP when performs routing."
    ::= { ipv6CurCfgStaticRouteEntry 5}

ipv6NewCfgStaticRouteTable OBJECT-TYPE
    SYNTAX  SEQUENCE OF Ipv6NewCfgStaticRouteEntry
    MAX-ACCESS  not-accessible
    STATUS  current
    DESCRIPTION
        "The table of ipv6 static routes in the current configuration block."
    ::= { ipStaticRouteCfg 5 }

ipv6NewCfgStaticRouteEntry OBJECT-TYPE
    SYNTAX  Ipv6NewCfgStaticRouteEntry
    MAX-ACCESS  not-accessible
    STATUS  current
    DESCRIPTION
        "A row in the static IP route table"
    INDEX   { ipv6NewCfgStaticRouteIndx }
    ::= { ipv6NewCfgStaticRouteTable 1 }

Ipv6NewCfgStaticRouteEntry ::= SEQUENCE {
    ipv6NewCfgStaticRouteIndx         Integer32,
    ipv6NewCfgStaticRouteDestIp       DisplayString,
    ipv6NewCfgStaticRouteMask         Integer32,
    ipv6NewCfgStaticRouteGateway      DisplayString,
    ipv6NewCfgStaticRouteAction       INTEGER,
    ipv6NewCfgStaticRouteInterface    Integer32
    }

ipv6NewCfgStaticRouteIndx OBJECT-TYPE
    SYNTAX  Integer32
    MAX-ACCESS  read-create
    STATUS  current
    DESCRIPTION
        "The index of the ipv6 static routing table."
    ::= { ipv6NewCfgStaticRouteEntry 1}

ipv6NewCfgStaticRouteDestIp OBJECT-TYPE
    SYNTAX  DisplayString (SIZE(0..40))
    MAX-ACCESS  read-create
    STATUS  current
    DESCRIPTION
        "The destination IPv6 address of this route.
         Address should be 4-byte haxadecimal colon notation. Valid IPv6 address should be in
         any of the following forms xxxx:xxxx:xxxx:xxxx:xxxx:xxxx:xxxx:xxxx or xxxx::xxxx:xxxx:xxxx:xxxx or ::xxxx"
    ::= { ipv6NewCfgStaticRouteEntry 2}

ipv6NewCfgStaticRouteMask OBJECT-TYPE
    SYNTAX  Integer32 (1..128)
    MAX-ACCESS  read-create
    STATUS  current
    DESCRIPTION
        "The prefix length associated with this IP address."
    ::= { ipv6NewCfgStaticRouteEntry 3}

ipv6NewCfgStaticRouteGateway OBJECT-TYPE
    SYNTAX  DisplayString (SIZE(0..40))
    MAX-ACCESS  read-create
    STATUS  current
    DESCRIPTION
        "The destination IPv6 gateway address of this route.
         Address should be 4-byte haxadecimal colon notation. Valid IPv6 address should be in
         any of the following forms xxxx:xxxx:xxxx:xxxx:xxxx:xxxx:xxxx:xxxx or xxxx::xxxx:xxxx:xxxx:xxxx or ::xxxx"
    ::= { ipv6NewCfgStaticRouteEntry 4}

ipv6NewCfgStaticRouteAction OBJECT-TYPE
    SYNTAX  INTEGER {
        other(1),
        delete(2)
       }
    MAX-ACCESS  read-create
    STATUS  current
    DESCRIPTION
        "When set to the value of 2 (delete), the entire row is deleted.
         When read, other is returned. Setting the value to anything other
         than 2(delete) has no effect on the state of the row."
    ::= { ipv6NewCfgStaticRouteEntry 5 }

ipv6NewCfgStaticRouteInterface OBJECT-TYPE
    SYNTAX  Integer32 (1..256)
    MAX-ACCESS  read-create
    STATUS  current
    DESCRIPTION
        "The IPv6 interface of this route.  The IPv6 address of the specified
         interface shall be use as source IP when performs routing."
    ::= { ipv6NewCfgStaticRouteEntry 6}


-- RIP version 1 Configuration


-- RIP version 2 Configuration

ripCurCfgIntfTable OBJECT-TYPE
    SYNTAX SEQUENCE OF RipCurCfgIntfEntry
    MAX-ACCESS not-accessible
    STATUS current
    DESCRIPTION
      "The table of RIP on IP interface configuration in the current_config."
    ::= { rip2Cfg 1 }

ripCurCfgIntfEntry OBJECT-TYPE
    SYNTAX RipCurCfgIntfEntry
    MAX-ACCESS not-accessible
    STATUS current
    DESCRIPTION
      "Information about  RIP on IP interface."
    INDEX { ripCurCfgIntfIndex }
    ::= { ripCurCfgIntfTable 1 }

RipCurCfgIntfEntry ::= SEQUENCE {
    ripCurCfgIntfIndex  	Integer32,
    ripCurCfgIntfVersion	INTEGER,
    ripCurCfgIntfSupply		INTEGER,
    ripCurCfgIntfListen		INTEGER,
    ripCurCfgIntfDefListen	INTEGER,
    ripCurCfgIntfTrigUpdate	INTEGER,
    ripCurCfgIntfMcastUpdate	INTEGER,
    ripCurCfgIntfPoisonReverse	INTEGER,
    ripCurCfgIntfState		INTEGER,
    ripCurCfgIntfMetric         INTEGER,
    ripCurCfgIntfAuth           INTEGER,
    ripCurCfgIntfKey            DisplayString,
    ripCurCfgIntfDefault	INTEGER
    }

ripCurCfgIntfIndex OBJECT-TYPE
    SYNTAX Integer32
    MAX-ACCESS read-only
    STATUS current
    DESCRIPTION
	"The interface number for which the RIP information is related."
    ::= { ripCurCfgIntfEntry 1}

ripCurCfgIntfVersion OBJECT-TYPE
    SYNTAX INTEGER {
        ripVersion1(1),
        ripVersion2(2),
        both(3)
        }
    MAX-ACCESS read-only
    STATUS current
    DESCRIPTION
        "RIP version."
    ::= { ripCurCfgIntfEntry 2 }

ripCurCfgIntfState OBJECT-TYPE
    SYNTAX INTEGER {
        enabled(1),
        disabled(2)
        }
    MAX-ACCESS read-only
    STATUS current
    DESCRIPTION
        "Enable or disable RIP protocol."
    ::= { ripCurCfgIntfEntry 3 }


ripCurCfgIntfListen OBJECT-TYPE
    SYNTAX INTEGER {
        enabled(1),
        disabled(2)
        }
    MAX-ACCESS read-only
    STATUS current
    DESCRIPTION
        "Enable or disable listening to route updates."
    ::= { ripCurCfgIntfEntry 4 }

ripCurCfgIntfDefListen OBJECT-TYPE
    SYNTAX  INTEGER {
        enabled(1),
        disabled(2)
        }
    MAX-ACCESS read-only
    STATUS obsolete
    DESCRIPTION
	"Enable or disable listening to default routes."
    ::= { ripCurCfgIntfEntry 5 }

ripCurCfgIntfTrigUpdate OBJECT-TYPE
    SYNTAX INTEGER {
        enabled(1),
        disabled(2)
        }
    MAX-ACCESS read-only
    STATUS current
    DESCRIPTION
	"Enable or disable triggered updates."
    ::= { ripCurCfgIntfEntry 6 }

ripCurCfgIntfMcastUpdate OBJECT-TYPE
    SYNTAX INTEGER {
        enabled(1),
        disabled(2)
        }
    MAX-ACCESS read-only
    STATUS current
    DESCRIPTION
	"Enable or disable multicast updates."
    ::= { ripCurCfgIntfEntry 7 }

ripCurCfgIntfPoisonReverse OBJECT-TYPE
    SYNTAX  INTEGER {
        enabled(1),
        disabled(2)
        }
    MAX-ACCESS read-only
    STATUS current
    DESCRIPTION
	"RIP poison reverse."
    ::= { ripCurCfgIntfEntry 8 }

ripCurCfgIntfSupply OBJECT-TYPE
    SYNTAX INTEGER {
        enabled(1),
        disabled(2)
        }
    MAX-ACCESS read-only
    STATUS current
    DESCRIPTION
        "Enable or disable supplying route updates."
    ::= { ripCurCfgIntfEntry 9 }

ripCurCfgIntfMetric OBJECT-TYPE
    SYNTAX  INTEGER (1..15)
    MAX-ACCESS read-only
    STATUS current
    DESCRIPTION
        "RIP route metric for this interface."
    ::= { ripCurCfgIntfEntry 10 }

ripCurCfgIntfAuth OBJECT-TYPE
    SYNTAX INTEGER {
        none(1),
        password(2)
        }
    MAX-ACCESS read-only
    STATUS current
    DESCRIPTION
        "The type of Authentication used on this interface."
    ::= { ripCurCfgIntfEntry 11 }

ripCurCfgIntfKey OBJECT-TYPE
    SYNTAX  DisplayString (SIZE(0..16))
    MAX-ACCESS  read-only
    STATUS  current
    DESCRIPTION
        "RIP update authentication password."
    ::= { ripCurCfgIntfEntry 12 }

ripCurCfgIntfDefault OBJECT-TYPE
    SYNTAX  INTEGER {
        both(1),
        listen(2),
        supply(3),
        none(4)
        }
    MAX-ACCESS read-only
    STATUS current
    DESCRIPTION
	"Specifies what RIP does with default routes."
    ::= { ripCurCfgIntfEntry 13 }

ripNewCfgIntfTable OBJECT-TYPE
    SYNTAX SEQUENCE OF RipNewCfgIntfEntry
    MAX-ACCESS not-accessible
    STATUS current
    DESCRIPTION
      "The table of RIP on IP interface configuration in the new_config."
    ::= { rip2Cfg 2 }

ripNewCfgIntfEntry OBJECT-TYPE
    SYNTAX RipNewCfgIntfEntry
    MAX-ACCESS not-accessible
    STATUS current
    DESCRIPTION
      "Information about  RIP on IP interface."
    INDEX { ripNewCfgIntfIndex }
    ::= { ripNewCfgIntfTable 1 }

RipNewCfgIntfEntry ::= SEQUENCE {
    ripNewCfgIntfIndex  	Integer32,
    ripNewCfgIntfVersion	INTEGER,
    ripNewCfgIntfSupply		INTEGER,
    ripNewCfgIntfListen		INTEGER,
    ripNewCfgIntfDefListen	INTEGER,
    ripNewCfgIntfTrigUpdate	INTEGER,
    ripNewCfgIntfMcastUpdate	INTEGER,
    ripNewCfgIntfPoisonReverse	INTEGER,
    ripNewCfgIntfState		INTEGER,
    ripNewCfgIntfMetric         INTEGER,
    ripNewCfgIntfAuth           INTEGER,
    ripNewCfgIntfKey            DisplayString,
    ripNewCfgIntfDefault	INTEGER
    }

ripNewCfgIntfIndex OBJECT-TYPE
    SYNTAX Integer32
    MAX-ACCESS read-only
    STATUS current
    DESCRIPTION
	"The interface number for which the RIP information is related."
    ::= { ripNewCfgIntfEntry 1}

ripNewCfgIntfVersion OBJECT-TYPE
    SYNTAX INTEGER {
        ripVersion1(1),
        ripVersion2(2),
        both(3)
        }
    MAX-ACCESS read-create
    STATUS current
    DESCRIPTION
        "RIP version."
    ::= { ripNewCfgIntfEntry 2 }

ripNewCfgIntfSupply OBJECT-TYPE
    SYNTAX INTEGER {
        enabled(1),
        disabled(2)
        }
    MAX-ACCESS read-create
    STATUS current
    DESCRIPTION
        "Enable or disable supplying route updates."
    ::= { ripNewCfgIntfEntry 3 }

ripNewCfgIntfListen OBJECT-TYPE
    SYNTAX INTEGER {
        enabled(1),
        disabled(2)
        }
    MAX-ACCESS read-create
    STATUS current
    DESCRIPTION
        "Enable or disable listening to route updates."
    ::= { ripNewCfgIntfEntry 4 }

ripNewCfgIntfDefListen OBJECT-TYPE
    SYNTAX INTEGER {
        enabled(1),
        disabled(2)
        }
    MAX-ACCESS read-create
    STATUS obsolete
    DESCRIPTION
	"Enable or disable listening to default routes."
    ::= { ripNewCfgIntfEntry 5 }

ripNewCfgIntfTrigUpdate OBJECT-TYPE
    SYNTAX INTEGER {
        enabled(1),
        disabled(2)
        }
    MAX-ACCESS read-create
    STATUS current
    DESCRIPTION
	"Enable or disable triggered updates."
    ::= { ripNewCfgIntfEntry 6 }

ripNewCfgIntfMcastUpdate OBJECT-TYPE
    SYNTAX INTEGER {
        enabled(1),
        disabled(2)
        }
    MAX-ACCESS read-create
    STATUS current
    DESCRIPTION
	"Enable or disable multicast updates."
    ::= { ripNewCfgIntfEntry 7 }

ripNewCfgIntfPoisonReverse OBJECT-TYPE
    SYNTAX INTEGER {
        enabled(1),
        disabled(2)
        }
    MAX-ACCESS read-create
    STATUS current
    DESCRIPTION
	"RIP poison reverse."
    ::= { ripNewCfgIntfEntry 8 }

ripNewCfgIntfState OBJECT-TYPE
    SYNTAX INTEGER {
        enabled(1),
        disabled(2)
        }
    MAX-ACCESS read-create
    STATUS current
    DESCRIPTION
        "Enable or disable RIP protocol."
    ::= { ripNewCfgIntfEntry 9 }

ripNewCfgIntfMetric OBJECT-TYPE
    SYNTAX  INTEGER (1..15)
    MAX-ACCESS read-write
    STATUS current
    DESCRIPTION
        "RIP route metric for this interface."
    ::= { ripNewCfgIntfEntry 10 }

ripNewCfgIntfAuth OBJECT-TYPE
    SYNTAX INTEGER {
        none(1),
        password(2)
        }
    MAX-ACCESS read-write
    STATUS current
    DESCRIPTION
        "The type of Authentication used on this interface."
    ::= { ripNewCfgIntfEntry 11 }

ripNewCfgIntfKey OBJECT-TYPE
    SYNTAX  DisplayString (SIZE(0..16))
    MAX-ACCESS  read-create
    STATUS  current
    DESCRIPTION
        "RIP update authentication password."
    ::= { ripNewCfgIntfEntry 12 }

ripNewCfgIntfDefault OBJECT-TYPE
    SYNTAX INTEGER {
        both(1),
        listen(2),
        supply(3),
        none(4)
        }
    MAX-ACCESS read-create
    STATUS current
    DESCRIPTION
	"Specifies what RIP does with default routes. The default routes
         action could be set to listen/supply/both/none."
    ::= { ripNewCfgIntfEntry 13 }

ripGeneral	OBJECT IDENTIFIER ::= { rip2Cfg 3 }

rip2CurCfgState OBJECT-TYPE
    SYNTAX INTEGER {
        on(1),
        off(2)
        }
    MAX-ACCESS read-only
    STATUS current
    DESCRIPTION
	"RIP global state."
    ::= { ripGeneral 1 }

rip2NewCfgState OBJECT-TYPE
    SYNTAX INTEGER {
        on(1),
        off(2)
        }
    MAX-ACCESS read-write
    STATUS current
    DESCRIPTION
	"Globally turn RIP on or off."
    ::= { ripGeneral 2 }

rip2CurCfgUpdatePeriod OBJECT-TYPE
      SYNTAX  INTEGER  (1..120)
      MAX-ACCESS  read-only
      STATUS  current
      DESCRIPTION
	      "Update Period in seconds."
      ::= { ripGeneral 3 }

rip2NewCfgUpdatePeriod OBJECT-TYPE
      SYNTAX  INTEGER  (1..120)
      MAX-ACCESS  read-write
      STATUS  current
      DESCRIPTION
	      "Update Period in seconds."
      ::= { ripGeneral 4 }

rip2CurCfgVip OBJECT-TYPE
      SYNTAX  INTEGER {
                enabled(2),
                disabled(3)
                }
      MAX-ACCESS  read-only
      STATUS  current
      DESCRIPTION
              "Advertise VIP Host Routes."
      ::= { ripGeneral 5 }

rip2NewCfgVip OBJECT-TYPE
      SYNTAX  INTEGER {
                enabled(2),
                disabled(3)
                }
      MAX-ACCESS  read-write
      STATUS  current
      DESCRIPTION
              "Advertise VIP Host Routes."
      ::= { ripGeneral 6 }

rip2CurCfgStaticSupply OBJECT-TYPE
      SYNTAX  INTEGER {
                enabled(2),
                disabled(3)
                }
      MAX-ACCESS  read-only
      STATUS  current
      DESCRIPTION
              "Advertise Static Routes."
      ::= { ripGeneral 7 }

rip2NewCfgStaticSupply OBJECT-TYPE
      SYNTAX  INTEGER {
                enabled(2),
                disabled(3)
                }
      MAX-ACCESS  read-write
      STATUS  current
      DESCRIPTION
              "Advertise Static Routes."
      ::= { ripGeneral 8 }

-- IP Forwarding Configuration

ipFwdGeneralCfg   OBJECT IDENTIFIER ::=  {ipForwardCfg 1 }

ipFwdCurCfgState OBJECT-TYPE
    SYNTAX  INTEGER {
        on(2),
        off(3)
	}
    MAX-ACCESS  read-only
    STATUS  current
    DESCRIPTION
        "IP forwarding global state."
    ::= { ipFwdGeneralCfg 1 }

ipFwdNewCfgState OBJECT-TYPE
    SYNTAX  INTEGER {
        on(2),
        off(3)
	}
    MAX-ACCESS  read-write
    STATUS  current
    DESCRIPTION
        "IP forwarding global state."
    ::= { ipFwdGeneralCfg 2 }

ipFwdCurCfgDirectedBcast OBJECT-TYPE
    SYNTAX INTEGER {
        enabled(2),
        disabled(3)
	}
    MAX-ACCESS read-only
    STATUS current
    DESCRIPTION
        "Enable or disable forwarding directed broadcasts."
    ::= { ipFwdGeneralCfg 3 }

ipFwdNewCfgDirectedBcast OBJECT-TYPE
    SYNTAX INTEGER {
        enabled(2),
        disabled(3)
	}
    MAX-ACCESS read-write
    STATUS current
    DESCRIPTION
        "Enable or disable forwarding directed broadcasts."
    ::= { ipFwdGeneralCfg 4 }

ipFwdCurCfgNoICMPRedirect OBJECT-TYPE
    SYNTAX INTEGER {
        enabled(2),
        disabled(3)
        }
    MAX-ACCESS read-only
    STATUS current
    DESCRIPTION
        "Enable or disable no icmp redirects."
    ::= { ipFwdGeneralCfg 5 }

ipFwdNewCfgNoICMPRedirect OBJECT-TYPE
    SYNTAX INTEGER {
        enabled(2),
        disabled(3)
        }
    MAX-ACCESS read-write
    STATUS current
    DESCRIPTION
        "Enable or disable no icmp redirects."
    ::= { ipFwdGeneralCfg 6 }

ipFwdCurCfgRtCache OBJECT-TYPE
    SYNTAX INTEGER {
        enabled(2),
        disabled(3)
        }
    MAX-ACCESS read-only
    STATUS current
    DESCRIPTION
        "Enable or disable SP Route Caching."
    ::= { ipFwdGeneralCfg 7 }

ipFwdNewCfgRtCache OBJECT-TYPE
    SYNTAX INTEGER {
        enabled(2),
        disabled(3)
        }
    MAX-ACCESS read-write
    STATUS current
    DESCRIPTION
        "Enable or disable SP Route Caching."
    ::= { ipFwdGeneralCfg 8 }

ipFwdPortTableMaxSize OBJECT-TYPE
    SYNTAX Integer32
    MAX-ACCESS read-only
    STATUS current
    DESCRIPTION
        "The maximum number of rows in the IP Port table."
    ::= { ipForwardCfg 2 }

ipFwdCurCfgPortTable OBJECT-TYPE
    SYNTAX  SEQUENCE OF IpFwdCurCfgPortEntry
    MAX-ACCESS  not-accessible
    STATUS  current
    DESCRIPTION
        "The table of ports and their forwarding states"
    ::= { ipForwardCfg 3 }

ipFwdCurCfgPortEntry OBJECT-TYPE
    SYNTAX  IpFwdCurCfgPortEntry
    MAX-ACCESS  not-accessible
    STATUS  current
    DESCRIPTION
        "A row in the ipFwdCurCfgPortTable "
    INDEX   { ipFwdCurCfgPortIndex }
    ::= { ipFwdCurCfgPortTable 1 }

IpFwdCurCfgPortEntry ::= SEQUENCE {
    ipFwdCurCfgPortIndex	Integer32,
    ipFwdCurCfgPortState	INTEGER
    }

ipFwdCurCfgPortIndex OBJECT-TYPE
    SYNTAX  Integer32
    MAX-ACCESS  read-only
    STATUS  current
    DESCRIPTION
        "The port number for which the forwarding state information pertains."
    ::= { ipFwdCurCfgPortEntry 1 }

ipFwdCurCfgPortState OBJECT-TYPE
    SYNTAX  INTEGER {
	enabled(2),
	disabled(3)
        }
    MAX-ACCESS  read-only
    STATUS  current
    DESCRIPTION
        "The forwarding state of the port."
    ::= { ipFwdCurCfgPortEntry 2 }

ipFwdNewCfgPortTable OBJECT-TYPE
    SYNTAX  SEQUENCE OF IpFwdNewCfgPortEntry
    MAX-ACCESS  not-accessible
    STATUS  current
    DESCRIPTION
        "The table of ports and their forwarding states"
    ::= { ipForwardCfg 4 }

ipFwdNewCfgPortEntry OBJECT-TYPE
    SYNTAX  IpFwdNewCfgPortEntry
    MAX-ACCESS  not-accessible
    STATUS  current
    DESCRIPTION
        "A row in the ipFwdNewCfgPortTable "
    INDEX   { ipFwdNewCfgPortIndex }
    ::= { ipFwdNewCfgPortTable 1 }

IpFwdNewCfgPortEntry ::= SEQUENCE {
    ipFwdNewCfgPortIndex           Integer32,
    ipFwdNewCfgPortState           INTEGER
    }

ipFwdNewCfgPortIndex OBJECT-TYPE
    SYNTAX  Integer32
    MAX-ACCESS  read-only
    STATUS  current
    DESCRIPTION
        "The port number for which the forwarding state information pertains."
    ::= { ipFwdNewCfgPortEntry 1 }

ipFwdNewCfgPortState OBJECT-TYPE
    SYNTAX  INTEGER {
        enabled(2),
        disabled(3)
        }
    MAX-ACCESS  read-write
    STATUS  current
    DESCRIPTION
        "The forwarding state of the port."
    ::= { ipFwdNewCfgPortEntry 2 }

ipFwdLocalTableMaxSize OBJECT-TYPE
    SYNTAX Integer32
    MAX-ACCESS read-only
    STATUS current
    DESCRIPTION
        "The maximum number of rows in the Local table."
    ::= { ipForwardCfg 5 }

ipFwdCurCfgLocalTable OBJECT-TYPE
    SYNTAX  SEQUENCE OF IpFwdCurCfgLocalEntry
    MAX-ACCESS  not-accessible
    STATUS  current
    DESCRIPTION
        "The table of local network definition."
    ::= { ipForwardCfg 6 }

ipFwdCurCfgLocalEntry OBJECT-TYPE
    SYNTAX  IpFwdCurCfgLocalEntry
    MAX-ACCESS  not-accessible
    STATUS  current
    DESCRIPTION
        "A row in the ipFwdCurCfgLocalTable "
    INDEX   { ipFwdCurCfgLocalIndex }
    ::= { ipFwdCurCfgLocalTable 1 }

IpFwdCurCfgLocalEntry ::= SEQUENCE {
    ipFwdCurCfgLocalIndex	Integer32,
    ipFwdCurCfgLocalSubnet	IpAddress,
    ipFwdCurCfgLocalMask	IpAddress
    }

ipFwdCurCfgLocalIndex OBJECT-TYPE
    SYNTAX  Integer32
    MAX-ACCESS  read-only
    STATUS  current
    DESCRIPTION
        "The index of ipFwdCurCfgLocalTable."
    ::= { ipFwdCurCfgLocalEntry 1 }

ipFwdCurCfgLocalSubnet OBJECT-TYPE
    SYNTAX  IpAddress
    MAX-ACCESS  read-only
    STATUS  current
    DESCRIPTION
        "The current local IP subnet."
    ::= { ipFwdCurCfgLocalEntry 2 }

ipFwdCurCfgLocalMask OBJECT-TYPE
    SYNTAX  IpAddress
    MAX-ACCESS  read-only
    STATUS  current
    DESCRIPTION
        "The current local IP subnet mask."
    ::= { ipFwdCurCfgLocalEntry 3 }

ipFwdNewCfgLocalTable OBJECT-TYPE
    SYNTAX  SEQUENCE OF IpFwdNewCfgLocalEntry
    MAX-ACCESS  not-accessible
    STATUS  current
    DESCRIPTION
        "The table of local network definition."
    ::= { ipForwardCfg 7 }

ipFwdNewCfgLocalEntry OBJECT-TYPE
    SYNTAX  IpFwdNewCfgLocalEntry
    MAX-ACCESS  not-accessible
    STATUS  current
    DESCRIPTION
        "A row in the ipFwdNewCfgLocalTable "
    INDEX   { ipFwdNewCfgLocalIndex }
    ::= { ipFwdNewCfgLocalTable 1 }

IpFwdNewCfgLocalEntry ::= SEQUENCE {
    ipFwdNewCfgLocalIndex	Integer32,
    ipFwdNewCfgLocalSubnet	IpAddress,
    ipFwdNewCfgLocalMask	IpAddress,
    ipFwdNewCfgLocalDelete      INTEGER
    }

ipFwdNewCfgLocalIndex OBJECT-TYPE
    SYNTAX  Integer32
    MAX-ACCESS  read-only
    STATUS  current
    DESCRIPTION
        "The index of ipFwdNewCfgLocalTable."
    ::= { ipFwdNewCfgLocalEntry 1 }

ipFwdNewCfgLocalSubnet OBJECT-TYPE
    SYNTAX  IpAddress
    MAX-ACCESS  read-create
    STATUS  current
    DESCRIPTION
        "The new local IP subnet."
    ::= { ipFwdNewCfgLocalEntry 2 }

ipFwdNewCfgLocalMask OBJECT-TYPE
    SYNTAX  IpAddress
    MAX-ACCESS  read-create
    STATUS  current
    DESCRIPTION
        "The new local IP subnet mask."
    ::= { ipFwdNewCfgLocalEntry 3 }

ipFwdNewCfgLocalDelete OBJECT-TYPE
    SYNTAX INTEGER {
        other(1),
        delete(2)
	}
    MAX-ACCESS read-create
    STATUS current
    DESCRIPTION
        "When set to the value of 2 (delete), the entire row is deleted.
         When read, other(1) is returned. Setting the value to anything
         other than 2(delete) has no effect on the state of the row."
    ::= { ipFwdNewCfgLocalEntry 4 }

--
-- ARP configuration
--
arpCurCfgReARPPeriod OBJECT-TYPE
    SYNTAX INTEGER (2..120)
    MAX-ACCESS read-only
    STATUS current
    DESCRIPTION
        "Re-ARP Period in seconds."
    ::= { arpCfg 1 }

arpNewCfgReARPPeriod OBJECT-TYPE
    SYNTAX  INTEGER (2..120)
    MAX-ACCESS  read-write
    STATUS  current
    DESCRIPTION
        "Re-ARP Period in seconds."
    ::= { arpCfg 2 }

--
-- IP Bootp Configration
--
ipCurCfgBootpAddr OBJECT-TYPE
    SYNTAX  IpAddress
    MAX-ACCESS  read-only
    STATUS  current
    DESCRIPTION
        "The IP address of BOOTP server."
    ::= { ipBootpCfg 1 }

ipNewCfgBootpAddr OBJECT-TYPE
    SYNTAX  IpAddress
    MAX-ACCESS  read-write
    STATUS  current
    DESCRIPTION
        "The IP address of BOOTP server."
    ::= { ipBootpCfg 2 }

ipCurCfgBootpAddr2 OBJECT-TYPE
    SYNTAX  IpAddress
    MAX-ACCESS  read-only
    STATUS  current
    DESCRIPTION
        "The IP address of second BOOTP server."
    ::= { ipBootpCfg 3 }

ipNewCfgBootpAddr2 OBJECT-TYPE
    SYNTAX  IpAddress
    MAX-ACCESS  read-write
    STATUS  current
    DESCRIPTION
        "The IP address of second BOOTP server."
    ::= { ipBootpCfg 4 }

ipCurCfgBootpState OBJECT-TYPE
    SYNTAX  INTEGER {
        enabled(2),
        disabled(3)
        }
    MAX-ACCESS  read-only
    STATUS  current
    DESCRIPTION
        "The state of BOOTP relay."
    ::= { ipBootpCfg 5 }

ipNewCfgBootpState OBJECT-TYPE
    SYNTAX  INTEGER {
        enabled(2),
        disabled(3)
        }
    MAX-ACCESS  read-write
    STATUS  current
    DESCRIPTION
        "The state of BOOTP relay."
    ::= { ipBootpCfg 6 }

-- VRRP (Virtual Router Redundantcy Protocol) Group

vrrpGeneral       OBJECT IDENTIFIER ::= { vrrpCfg 1 }

vrrpCurCfgGenState OBJECT-TYPE
    SYNTAX  INTEGER {
        enabled(1),
        disabled(2)
        }
    MAX-ACCESS  read-only
    STATUS  current
    DESCRIPTION
        "Enable or disable VRRP operation globally."
    ::= { vrrpGeneral 1 }

vrrpNewCfgGenState OBJECT-TYPE
    SYNTAX  INTEGER {
        enabled(1),
        disabled(2)
        }
    MAX-ACCESS  read-write
    STATUS  current
    DESCRIPTION
        "Enable or disable VRRP operation globally."
    ::= { vrrpGeneral 2 }

vrrpCurCfgGenTckVirtRtrInc OBJECT-TYPE
    SYNTAX  INTEGER (0..254)
    MAX-ACCESS  read-only
    STATUS  current
    DESCRIPTION
        "The increment of VRRP virtual router priority. The priority is
         adjusted by tracking the state of other virtual routers."
    ::= { vrrpGeneral 3 }

vrrpNewCfgGenTckVirtRtrInc OBJECT-TYPE
    SYNTAX  INTEGER (0..254)
    MAX-ACCESS  read-write
    STATUS  current
    DESCRIPTION
        "The increment of VRRP virtual router priority. The priority is
         adjusted by tracking the state of other virtual routers."
    ::= { vrrpGeneral 4 }

vrrpCurCfgGenTckIpIntfInc OBJECT-TYPE
    SYNTAX  INTEGER (0..254)
    MAX-ACCESS  read-only
    STATUS  current
    DESCRIPTION
        "The increment of VRRP virtual router priority. The priority is
         adjusted by tracking the state of other router interfaces."
    ::= { vrrpGeneral 5 }

vrrpNewCfgGenTckIpIntfInc OBJECT-TYPE
    SYNTAX  INTEGER (0..254)
    MAX-ACCESS  read-write
    STATUS  current
    DESCRIPTION
        "The increment of VRRP virtual router priority. The priority is
         adjusted by tracking the state of other router interfaces."
    ::= { vrrpGeneral 6 }

vrrpCurCfgGenTckVlanPortInc OBJECT-TYPE
    SYNTAX  INTEGER (0..254)
    MAX-ACCESS  read-only
    STATUS  current
    DESCRIPTION
        "The increment of VRRP virtual router priority. The priority is
         adjusted by tracking the port state of ports that belongs to the
         same virtual LAN as the virtual router."
    ::= { vrrpGeneral 7 }

vrrpNewCfgGenTckVlanPortInc OBJECT-TYPE
    SYNTAX  INTEGER (0..254)
    MAX-ACCESS  read-write
    STATUS  current
    DESCRIPTION
        "The increment of VRRP virtual router priority. The priority is
         adjusted by tracking the port state of ports that belongs to the
         same virtual LAN as the virtual router."
    ::= { vrrpGeneral 8 }

vrrpCurCfgGenTckL4PortInc OBJECT-TYPE
    SYNTAX  INTEGER (0..254)
    MAX-ACCESS  read-only
    STATUS  current
    DESCRIPTION
        "The increment of VRRP virtual router priority. The priority is
         adjusted by tracking the Layer 4 port states. This is valid when
         virtual server is configured as a VRRP virtual router."
    ::= { vrrpGeneral 9 }

vrrpNewCfgGenTckL4PortInc OBJECT-TYPE
    SYNTAX  INTEGER (0..254)
    MAX-ACCESS  read-write
    STATUS  current
    DESCRIPTION
        "The increment of VRRP virtual router priority. The priority is
         adjusted by tracking the Layer 4 port states. This is valid when
         virtual server is configured as a VRRP virtual router."
    ::= { vrrpGeneral 10 }

vrrpCurCfgGenTckRServerInc OBJECT-TYPE
    SYNTAX  INTEGER (0..254)
    MAX-ACCESS  read-only
    STATUS  current
    DESCRIPTION
        "The increment of VRRP virtual router priority. The priority is
         adjusted by tracking the state of real servers under the virtual
         server which is configured as a VRRP virtual router."
    ::= { vrrpGeneral 11 }

vrrpNewCfgGenTckRServerInc OBJECT-TYPE
    SYNTAX  INTEGER (0..254)
    MAX-ACCESS  read-write
    STATUS  current
    DESCRIPTION
        "The increment of VRRP virtual router priority. The priority is
         adjusted by tracking the state of real servers under the virtual
         server which is configured as a VRRP virtual router."
    ::= { vrrpGeneral 12 }

vrrpCurCfgGenTckHsrpInc OBJECT-TYPE
    SYNTAX  INTEGER (0..254)
    MAX-ACCESS  read-only
    STATUS  current
    DESCRIPTION
        "The increment of VRRP virtual router priority.  The
	 priority is adjusted by tracking the HSRP advertisements."
    ::= { vrrpGeneral 13 }

vrrpNewCfgGenTckHsrpInc OBJECT-TYPE
    SYNTAX  INTEGER (0..254)
    MAX-ACCESS  read-write
    STATUS  current
    DESCRIPTION
        "The increment of VRRP virtual router priority.  The
         priority is adjusted by tracking the HSRP advertisements."
    ::= { vrrpGeneral 14 }

vrrpCurCfgGenHotstandby OBJECT-TYPE
    SYNTAX  INTEGER {
        enabled(1),
        disabled(2)
        }
    MAX-ACCESS  read-only
    STATUS  current
    DESCRIPTION
        "Enable or disable hotstandby processing."
    ::= { vrrpGeneral 15 }

vrrpNewCfgGenHotstandby OBJECT-TYPE
    SYNTAX  INTEGER {
        enabled(1),
        disabled(2)
        }
    MAX-ACCESS  read-write
    STATUS  current
    DESCRIPTION
        "Enable or disable hotstandby processing."
    ::= { vrrpGeneral 16 }

vrrpCurCfgGenTckHsrvInc OBJECT-TYPE
        SYNTAX  INTEGER (0..254)
        MAX-ACCESS  read-only
        STATUS  current
        DESCRIPTION
                "The increment of VRRP virtual router priority.  The
                 priority is adjusted by tracking the HSRP advertisements
                 by VLAN."
        ::= { vrrpGeneral 17 }

vrrpNewCfgGenTckHsrvInc OBJECT-TYPE
        SYNTAX  INTEGER (0..254)
        MAX-ACCESS  read-write
        STATUS  current
        DESCRIPTION
                "The increment of VRRP virtual router priority.  The
                 priority is adjusted by tracking the HSRP advertisements
                 by VLAN."
        ::= { vrrpGeneral 18 }

vrrpCurCfgGenHoldoff OBJECT-TYPE
        SYNTAX  INTEGER (0..255)
        MAX-ACCESS  read-only
        STATUS  current
        DESCRIPTION
                "The time for VRRP virtual router to hold before it
                 begins to change state to backup or master state."
        ::= { vrrpGeneral 19 }

vrrpNewCfgGenHoldoff OBJECT-TYPE
        SYNTAX  INTEGER (0..255)
        MAX-ACCESS  read-write
        STATUS  current
        DESCRIPTION
                "The time for VRRP virtual router to hold before it
                 begins to change state to backup or master state."
        ::= { vrrpGeneral 20 }


vrrpVirtRtrTableMaxSize OBJECT-TYPE
    SYNTAX Integer32
    MAX-ACCESS read-only
    STATUS current
    DESCRIPTION
        "The maximum number of entries in VRRP virtual router table."
    ::= { vrrpCfg 2 }

vrrpCurCfgVirtRtrTable OBJECT-TYPE
    SYNTAX  SEQUENCE OF VrrpCurCfgVirtRtrTableEntry
    MAX-ACCESS  not-accessible
    STATUS  current
    DESCRIPTION
        "The table of VRRP virtual routers configuration in current_config."
    ::= { vrrpCfg 3 }

vrrpCurCfgVirtRtrTableEntry OBJECT-TYPE
    SYNTAX  VrrpCurCfgVirtRtrTableEntry
    MAX-ACCESS  not-accessible
    STATUS  current
    DESCRIPTION
        "Information about a VRRP virtual router."
    INDEX   { vrrpCurCfgVirtRtrIndx }
    ::= { vrrpCurCfgVirtRtrTable 1 }

VrrpCurCfgVirtRtrTableEntry ::= SEQUENCE {
    vrrpCurCfgVirtRtrIndx         Integer32,
    vrrpCurCfgVirtRtrID           INTEGER,
    vrrpCurCfgVirtRtrAddr         IpAddress,
    vrrpCurCfgVirtRtrIfIndex      Integer32,
    vrrpCurCfgVirtRtrInterval     INTEGER,
    vrrpCurCfgVirtRtrPriority     INTEGER,
    vrrpCurCfgVirtRtrPreempt      INTEGER,
    vrrpCurCfgVirtRtrState        INTEGER,
    vrrpCurCfgVirtRtrSharing      INTEGER,
    vrrpCurCfgVirtRtrTckVirtRtr   INTEGER,
    vrrpCurCfgVirtRtrTckIpIntf    INTEGER,
    vrrpCurCfgVirtRtrTckL4Port    INTEGER,
    vrrpCurCfgVirtRtrTckRServer   INTEGER,
    vrrpCurCfgVirtRtrTckHsrp      INTEGER,
    vrrpCurCfgVirtRtrTckHsrv      INTEGER,
    vrrpCurCfgVirtRtrTckVlanPort  INTEGER,
    vrrpCurCfgVirtRtrVersion      INTEGER,
    vrrpCurCfgVirtRtrIpv6Addr     DisplayString,
    vrrpCurCfgVirtRtrIpv6Interval INTEGER
    }

vrrpCurCfgVirtRtrIndx OBJECT-TYPE
    SYNTAX  Integer32
    MAX-ACCESS  read-only
    STATUS  current
    DESCRIPTION
        "The VRRP virtual router table index."
    ::= { vrrpCurCfgVirtRtrTableEntry 1 }

vrrpCurCfgVirtRtrID OBJECT-TYPE
    SYNTAX  INTEGER (1..1024)
    MAX-ACCESS  read-only
    STATUS  current
    DESCRIPTION
        "The VRRP virtual router identifier."
    ::= { vrrpCurCfgVirtRtrTableEntry 2 }

vrrpCurCfgVirtRtrAddr OBJECT-TYPE
    SYNTAX  IpAddress
    MAX-ACCESS  read-only
    STATUS  current
    DESCRIPTION
        "The VRRP virtual router IP address."
    ::= { vrrpCurCfgVirtRtrTableEntry 3 }

vrrpCurCfgVirtRtrIfIndex OBJECT-TYPE
    SYNTAX  Integer32
    MAX-ACCESS  read-only
    STATUS  current
    DESCRIPTION
        "The IfIndex that the VRRP virtual router is representing."
    ::= { vrrpCurCfgVirtRtrTableEntry 4 }

vrrpCurCfgVirtRtrInterval OBJECT-TYPE
    SYNTAX  INTEGER (1..255)
    MAX-ACCESS  read-only
    STATUS  current
    DESCRIPTION
        "The time interval between VRRP advertisements in seconds."
    ::= { vrrpCurCfgVirtRtrTableEntry 5 }

vrrpCurCfgVirtRtrPriority OBJECT-TYPE
    SYNTAX  INTEGER (1..254)
    MAX-ACCESS  read-only
    STATUS  current
    DESCRIPTION
        "The priority value to be used by the specified VRRP virtual routers."
    ::= { vrrpCurCfgVirtRtrTableEntry 6 }

vrrpCurCfgVirtRtrPreempt OBJECT-TYPE
    SYNTAX  INTEGER {
        enabled(1),
        disabled(2)
        }
    MAX-ACCESS  read-only
    STATUS  current
    DESCRIPTION
        "This is for controlling whether a higher priority Backup
          VRRP virtual router preempts a low priority Master.

          enabled(1)  - allow preemption
          disabled(2) - prohibit preemption"
    ::= { vrrpCurCfgVirtRtrTableEntry 7 }

vrrpCurCfgVirtRtrState OBJECT-TYPE
    SYNTAX  INTEGER {
        enabled(1),
        disabled(2)
        }
    MAX-ACCESS  read-only
    STATUS  current
    DESCRIPTION
        "Enable or disable the VRRP virtual router."
    ::= { vrrpCurCfgVirtRtrTableEntry 8 }

vrrpCurCfgVirtRtrSharing OBJECT-TYPE
    SYNTAX  INTEGER {
        enabled(1),
        disabled(2)
        }
    MAX-ACCESS  read-only
    STATUS  current
    DESCRIPTION
        "Enable or disable load sharing of non-master virtual router."
    ::= { vrrpCurCfgVirtRtrTableEntry 9 }

vrrpCurCfgVirtRtrTckVirtRtr OBJECT-TYPE
    SYNTAX  INTEGER {
        enabled(1),
        disabled(2)
        }
    MAX-ACCESS  read-only
    STATUS  current
    DESCRIPTION
        "Enable or disable tracking other virtual routers for priority
         adjustment. The priority increment is defined
         in vrrpCurCfgGenTckVirtRtrInc."
    ::= { vrrpCurCfgVirtRtrTableEntry 10 }

vrrpCurCfgVirtRtrTckIpIntf OBJECT-TYPE
    SYNTAX  INTEGER {
        enabled(1),
        disabled(2)
        }
    MAX-ACCESS  read-only
    STATUS  current
    DESCRIPTION
        "Enable or disable tracking other router interfaces for
	 priority adjustment. The priority increment is defined
	 in vrrpCurCfgGenTckIpIntfInc."
    ::= { vrrpCurCfgVirtRtrTableEntry 11 }

vrrpCurCfgVirtRtrTckVlanPort OBJECT-TYPE
    SYNTAX  INTEGER {
        enabled(1),
        disabled(2)
        }
    MAX-ACCESS  read-only
    STATUS  current
    DESCRIPTION
        "Enable or disable tracking port state of VLAN ports
	 for priority adjustment. The priority increment is
	 defined in vrrpCurCfgGenTckVlanPortInc."
    ::= { vrrpCurCfgVirtRtrTableEntry 12 }

vrrpCurCfgVirtRtrTckL4Port OBJECT-TYPE
    SYNTAX  INTEGER {
        enabled(1),
        disabled(2)
        }
    MAX-ACCESS  read-only
    STATUS  current
    DESCRIPTION
        "Enable or disable tracking Layer 4 port states for
	 priority adjustment.  the priority increment is defined
	 in vrrpCurCfgGenTckL4PortInc.  This is applied when
	 virtual server is configured as a VRRP virtual router."
    ::= { vrrpCurCfgVirtRtrTableEntry 13 }

vrrpCurCfgVirtRtrTckRServer OBJECT-TYPE
    SYNTAX  INTEGER {
        enabled(1),
        disabled(2)
        }
    MAX-ACCESS  read-only
    STATUS  current
    DESCRIPTION
        "Enable or disable tracking real server states for
	 priority adjustment.  the priority increment is defined
	 in vrrpCurCfgGenTckRServerInc.  This is applied when
	 virtual server is configured as a VRRP virtual router."
    ::= { vrrpCurCfgVirtRtrTableEntry 14 }

vrrpCurCfgVirtRtrTckHsrp OBJECT-TYPE
    SYNTAX  INTEGER {
        enabled(1),
        disabled(2)
        }
    MAX-ACCESS  read-only
    STATUS  current
    DESCRIPTION
        "Enable or disable tracking HSRP advertisements for
	 priority adjustment.  the priority increment is defined
	 in vrrpCurCfgGenTckHsrpInc.  This is applied when
	 virtual server is configured as a VRRP virtual router."
    ::= { vrrpCurCfgVirtRtrTableEntry 15 }

vrrpCurCfgVirtRtrTckHsrv OBJECT-TYPE
        SYNTAX  INTEGER {
                enabled(1),
                disabled(2)
                }
        MAX-ACCESS  read-only
        STATUS  current
        DESCRIPTION
                "Enable or disable tracking HSRP advertisements by VLAN for
                 priority adjustment.  The priority increment is defined
                 in vrrpCurCfgGenTckHsrvInc.  This is applied when
                 virtual server is configured as a VRRP virtual router."
        ::= { vrrpCurCfgVirtRtrTableEntry 16 }

vrrpCurCfgVirtRtrVersion OBJECT-TYPE
     SYNTAX  INTEGER {
         v4(1),
         v6(2)
        }
     MAX-ACCESS  read-only
     STATUS  current
     DESCRIPTION
         "The VRRP virtual router IP Version."
     ::= { vrrpCurCfgVirtRtrTableEntry 17 }

vrrpCurCfgVirtRtrIpv6Addr OBJECT-TYPE
    SYNTAX   DisplayString (SIZE(0..40))
    MAX-ACCESS  read-only
    STATUS  current
    DESCRIPTION
        "The IPv6 address of the virtual router. Address should be 4-byte
         haxadecimal colon notation.
         Valid IPv6 address should be in any of the following forms
         xxxx:xxxx:xxxx:xxxx:xxxx:xxxx:xxxx:xxxx or
         xxxx::xxxx:xxxx:xxxx:xxxx or ::xxxx"
    ::= { vrrpCurCfgVirtRtrTableEntry 18 }

vrrpCurCfgVirtRtrIpv6Interval OBJECT-TYPE
    SYNTAX  INTEGER (1..1045)
    MAX-ACCESS  read-only
    STATUS  current
    DESCRIPTION
        "The time interval between VRRP advertisements in seconds."
    ::= { vrrpCurCfgVirtRtrTableEntry 19 }

vrrpNewCfgVirtRtrTable OBJECT-TYPE
    SYNTAX  SEQUENCE OF VrrpNewCfgVirtRtrTableEntry
    MAX-ACCESS  not-accessible
    STATUS  current
    DESCRIPTION
        "The table of VRRP virtual routers configuration in current_config."
    ::= { vrrpCfg 4 }

vrrpNewCfgVirtRtrTableEntry OBJECT-TYPE
    SYNTAX  VrrpNewCfgVirtRtrTableEntry
    MAX-ACCESS  not-accessible
    STATUS  current
    DESCRIPTION
        "Information about a VRRP virtual router."
    INDEX   { vrrpNewCfgVirtRtrIndx }
    ::= { vrrpNewCfgVirtRtrTable 1 }

VrrpNewCfgVirtRtrTableEntry ::= SEQUENCE {
    vrrpNewCfgVirtRtrIndx         Integer32,
    vrrpNewCfgVirtRtrID           INTEGER,
    vrrpNewCfgVirtRtrAddr         IpAddress,
    vrrpNewCfgVirtRtrIfIndex      Integer32,
    vrrpNewCfgVirtRtrInterval     INTEGER,
    vrrpNewCfgVirtRtrPriority     INTEGER,
    vrrpNewCfgVirtRtrPreempt      INTEGER,
    vrrpNewCfgVirtRtrState        INTEGER,
    vrrpNewCfgVirtRtrDelete       INTEGER,
    vrrpNewCfgVirtRtrSharing      INTEGER,
    vrrpNewCfgVirtRtrTckVirtRtr   INTEGER,
    vrrpNewCfgVirtRtrTckIpIntf    INTEGER,
    vrrpNewCfgVirtRtrTckL4Port    INTEGER,
    vrrpNewCfgVirtRtrTckRServer   INTEGER,
    vrrpNewCfgVirtRtrTckHsrp      INTEGER,
    vrrpNewCfgVirtRtrTckHsrv      INTEGER,
    vrrpNewCfgVirtRtrTckVlanPort  INTEGER,
    vrrpNewCfgVirtRtrVersion      INTEGER,
    vrrpNewCfgVirtRtrIpv6Addr     DisplayString,
    vrrpNewCfgVirtRtrIpv6Interval INTEGER
    }

vrrpNewCfgVirtRtrIndx OBJECT-TYPE
    SYNTAX  Integer32
    MAX-ACCESS  read-only
    STATUS  current
    DESCRIPTION
        "The VRRP virtual router table index."
    ::= { vrrpNewCfgVirtRtrTableEntry 1 }

vrrpNewCfgVirtRtrID OBJECT-TYPE
    SYNTAX  INTEGER (1..1024)
    MAX-ACCESS  read-create
    STATUS  current
    DESCRIPTION
        "The VRRP virtual router identifier."
    ::= { vrrpNewCfgVirtRtrTableEntry 2 }

vrrpNewCfgVirtRtrAddr OBJECT-TYPE
    SYNTAX  IpAddress
    MAX-ACCESS  read-create
    STATUS  current
    DESCRIPTION
        "The VRRP virtual router IP address."
    ::= { vrrpNewCfgVirtRtrTableEntry 3 }

vrrpNewCfgVirtRtrIfIndex OBJECT-TYPE
    SYNTAX  Integer32
    MAX-ACCESS  read-create
    STATUS  current
    DESCRIPTION
        "The IfIndex that the VRRP virtual router is representing."
   ::= { vrrpNewCfgVirtRtrTableEntry 4 }

vrrpNewCfgVirtRtrInterval OBJECT-TYPE
    SYNTAX  INTEGER (1..255)
    MAX-ACCESS  read-create
    STATUS  current
    DESCRIPTION
        "The time interval between VRRP advertisements in seconds."
    ::= { vrrpNewCfgVirtRtrTableEntry 5 }

vrrpNewCfgVirtRtrPriority OBJECT-TYPE
    SYNTAX  INTEGER (1..254)
    MAX-ACCESS  read-create
    STATUS  current
    DESCRIPTION
        "The priority value to be used by the specified VRRP virtual router."
    ::= { vrrpNewCfgVirtRtrTableEntry 6 }

vrrpNewCfgVirtRtrPreempt OBJECT-TYPE
    SYNTAX  INTEGER {
        enabled(1),
        disabled(2)
        }
    MAX-ACCESS  read-create
    STATUS  current
    DESCRIPTION
        "This is for controlling whether a higher priority Backup
         VRRP virtual router preempts a low priority Master.

         enabled(1)  - allow preemption
         disabled(2) - prohibit preemption"
    ::= { vrrpNewCfgVirtRtrTableEntry 7 }

vrrpNewCfgVirtRtrState OBJECT-TYPE
    SYNTAX  INTEGER {
        enabled(1),
        disabled(2)
        }
    MAX-ACCESS  read-create
    STATUS  current
    DESCRIPTION
        "Enable or disable the VRRP virtual router."
    ::= { vrrpNewCfgVirtRtrTableEntry 8 }

vrrpNewCfgVirtRtrDelete OBJECT-TYPE
    SYNTAX  INTEGER {
	other(1),
        delete(2)
	}
    MAX-ACCESS  read-create
    STATUS  current
    DESCRIPTION
        "When set to the value of 2 (delete), the entire row is deleted.
         When read, other(1) is returned. Setting the value to anything
         other than delete(2) has no effect on the state of the row."
    ::= { vrrpNewCfgVirtRtrTableEntry 9 }

vrrpNewCfgVirtRtrSharing OBJECT-TYPE
    SYNTAX  INTEGER {
        enabled(1),
        disabled(2)
        }
    MAX-ACCESS  read-create
    STATUS  current
    DESCRIPTION
        "Enable or disable load sharing of non-master virtual router."
    ::= { vrrpNewCfgVirtRtrTableEntry 10 }

vrrpNewCfgVirtRtrTckVirtRtr OBJECT-TYPE
    SYNTAX  INTEGER {
        enabled(1),
        disabled(2)
        }
    MAX-ACCESS  read-create
    STATUS  current
    DESCRIPTION
        "Enable or disable tracking other virtual routers for
	 priority adjustment.  the priority increment is defined
	 in vrrpNewCfgGenTckVirtRtrInc."
    ::= { vrrpNewCfgVirtRtrTableEntry 11 }

vrrpNewCfgVirtRtrTckIpIntf OBJECT-TYPE
    SYNTAX  INTEGER {
        enabled(1),
        disabled(2)
        }
     MAX-ACCESS  read-create
     STATUS  current
     DESCRIPTION
         "Enable or disable tracking other router interfaces for
	  priority adjustment.  the priority increment is defined
	  in vrrpNewCfgGenTckIpIntfInc."
    ::= { vrrpNewCfgVirtRtrTableEntry 12 }

vrrpNewCfgVirtRtrTckVlanPort OBJECT-TYPE
    SYNTAX  INTEGER {
        enabled(1),
        disabled(2)
        }
    MAX-ACCESS  read-create
    STATUS  current
    DESCRIPTION
        "Enable or disable tracking port state of VLAN ports
	 for priority adjustment.  the priority increment is
	 defined in vrrpNewCfgGenTckVlanPortInc."
    ::= { vrrpNewCfgVirtRtrTableEntry 13 }

vrrpNewCfgVirtRtrTckL4Port OBJECT-TYPE
    SYNTAX  INTEGER {
        enabled(1),
        disabled(2)
        }
     MAX-ACCESS  read-create
     STATUS  current
     DESCRIPTION
         "Enable or disable tracking Layer 4 port states for
	  priority adjustment.  the priority increment is defined
	  in vrrpNewCfgGenTckL4PortInc.  This is applied when
	  virtual server is configured as a VRRP virtual router."
    ::= { vrrpNewCfgVirtRtrTableEntry 14 }

vrrpNewCfgVirtRtrTckRServer OBJECT-TYPE
    SYNTAX  INTEGER {
        enabled(1),
        disabled(2)
        }
    MAX-ACCESS  read-create
    STATUS  current
    DESCRIPTION
        "Enable or disable tracking real server states for
	 priority adjustment.  the priority increment is defined
	 in vrrpNewCfgGenTckRServerInc.  This is applied when
	 virtual server is configured as a VRRP virtual router."
    ::= { vrrpNewCfgVirtRtrTableEntry 15 }

vrrpNewCfgVirtRtrTckHsrp OBJECT-TYPE
    SYNTAX  INTEGER {
        enabled(1),
        disabled(2)
        }
    MAX-ACCESS  read-create
    STATUS  current
    DESCRIPTION
        "Enable or disable tracking HSRP advertisements for
	 priority adjustment.  the priority increment is defined
	 in vrrpNewCfgGenTckHsrpInc.  This is applied when
	 virtual server is configured as a VRRP virtual router."
    ::= { vrrpNewCfgVirtRtrTableEntry 16 }

vrrpNewCfgVirtRtrTckHsrv OBJECT-TYPE
        SYNTAX  INTEGER {
                enabled(1),
                disabled(2)
                }
        MAX-ACCESS  read-create
        STATUS  current
        DESCRIPTION
                "Enable or disable tracking HSRP by VLAN advertisements for
                 priority adjustment.  The priority increment is defined
                 in vrrpNewCfgGenTckHsrvInc.  This is applied when
                 virtual server is configured as a VRRP virtual router."
        ::= { vrrpNewCfgVirtRtrTableEntry 17 }

vrrpNewCfgVirtRtrVersion OBJECT-TYPE
     SYNTAX  INTEGER {
         v4(1),
         v6(2)
        }
     MAX-ACCESS  read-create
     STATUS  current
     DESCRIPTION
         "The VRRP virtual router IP Version."
     ::= { vrrpNewCfgVirtRtrTableEntry 18 }

vrrpNewCfgVirtRtrIpv6Addr OBJECT-TYPE
    SYNTAX   DisplayString (SIZE(0..40))
    MAX-ACCESS  read-create
    STATUS  current
    DESCRIPTION
        "The IPv6 address of the virtual router. Address should be 4-byte
         haxadecimal colon notation.
         Valid IPv6 address should be in any of the following forms
         xxxx:xxxx:xxxx:xxxx:xxxx:xxxx:xxxx:xxxx or
         xxxx::xxxx:xxxx:xxxx:xxxx or ::xxxx"
    ::= { vrrpNewCfgVirtRtrTableEntry 19 }

vrrpNewCfgVirtRtrIpv6Interval OBJECT-TYPE
    SYNTAX  INTEGER (1..4095)
    MAX-ACCESS  read-create
    STATUS  current
    DESCRIPTION
        "The time interval between VRRP advertisements in seconds."
    ::= { vrrpNewCfgVirtRtrTableEntry 20 }

-- VRRP Interface Table

vrrpIfTableMaxSize OBJECT-TYPE
    SYNTAX Integer32
    MAX-ACCESS read-only
    STATUS current
    DESCRIPTION
        "The maximum number of entries in VRRP interface table."
    ::= { vrrpCfg 5 }

vrrpCurCfgIfTable OBJECT-TYPE
    SYNTAX  SEQUENCE OF VrrpCurCfgIfTableEntry
    MAX-ACCESS  not-accessible
    STATUS  current
    DESCRIPTION
        "The table of VRRP interface configuration in current_config."
    ::= { vrrpCfg 6 }

vrrpCurCfgIfTableEntry OBJECT-TYPE
    SYNTAX  VrrpCurCfgIfTableEntry
    MAX-ACCESS  not-accessible
    STATUS  current
    DESCRIPTION
        "Information about a VRRP interface."
    INDEX   { vrrpCurCfgIfIndx }
    ::= { vrrpCurCfgIfTable 1 }

VrrpCurCfgIfTableEntry ::= SEQUENCE {
    vrrpCurCfgIfIndx         Integer32,
    vrrpCurCfgIfAuthType     INTEGER,
    vrrpCurCfgIfPasswd       DisplayString,
    vrrpCurCfgIfIpAddr       IpAddress
    }

vrrpCurCfgIfIndx OBJECT-TYPE
    SYNTAX  Integer32
    MAX-ACCESS  read-only
    STATUS  current
    DESCRIPTION
        "The VRRP interface index.  This is eqivalent to IfIndex."
    ::= { vrrpCurCfgIfTableEntry 1 }

vrrpCurCfgIfAuthType OBJECT-TYPE
    SYNTAX  INTEGER {
        none(1),
        simple-text-password(2)
        }
    MAX-ACCESS  read-only
    STATUS  current
    DESCRIPTION
        "Type of authentication being used.
	 none(1) - no authentication
	 simple-text-password(2) - use password specified in
         vrrpCurCfgIfPasswd for authentication."
    ::= { vrrpCurCfgIfTableEntry 2 }

vrrpCurCfgIfPasswd OBJECT-TYPE
    SYNTAX  DisplayString (SIZE(0..7))
    MAX-ACCESS  read-only
    STATUS  current
    DESCRIPTION
        "The password for authentication."
    ::= { vrrpCurCfgIfTableEntry 3 }

vrrpCurCfgIfIpAddr OBJECT-TYPE
    SYNTAX IpAddress
    MAX-ACCESS read-only
    STATUS current
    DESCRIPTION
    "The IP address of the VRRP interface.This is eqivalent to ipCurCfgIntfAddr."
    ::= { vrrpCurCfgIfTableEntry 4 }

vrrpNewCfgIfTable OBJECT-TYPE
    SYNTAX  SEQUENCE OF VrrpNewCfgIfTableEntry
    MAX-ACCESS  not-accessible
    STATUS  current
    DESCRIPTION
        "The table of VRRP interface configuration in current_config."
    ::= { vrrpCfg 7 }

vrrpNewCfgIfTableEntry OBJECT-TYPE
    SYNTAX  VrrpNewCfgIfTableEntry
    MAX-ACCESS  not-accessible
    STATUS  current
    DESCRIPTION
        "Information about a VRRP interface."
    INDEX   { vrrpNewCfgIfIndx }
    ::= { vrrpNewCfgIfTable 1 }

VrrpNewCfgIfTableEntry ::= SEQUENCE {
    vrrpNewCfgIfIndx         Integer32,
    vrrpNewCfgIfAuthType     INTEGER,
    vrrpNewCfgIfPasswd       DisplayString,
    vrrpNewCfgIfDelete       INTEGER
    }

vrrpNewCfgIfIndx OBJECT-TYPE
    SYNTAX  Integer32
    MAX-ACCESS  read-only
    STATUS  current
    DESCRIPTION
        "The VRRP interface index.  This is eqivalent to IfIndex."
    ::= { vrrpNewCfgIfTableEntry 1 }

vrrpNewCfgIfAuthType OBJECT-TYPE
    SYNTAX  INTEGER {
        none(1),
        simple-text-password(2)
        }
    MAX-ACCESS  read-create
    STATUS  current
    DESCRIPTION
        "Type of authentication being used.
	 none(1) - no authentication
	 simple-text-password(2) - use password specified in
         vrrpNewCfgIfPasswd for authentication."
    ::= { vrrpNewCfgIfTableEntry 2 }

vrrpNewCfgIfPasswd OBJECT-TYPE
    SYNTAX  DisplayString (SIZE(0..7))
    MAX-ACCESS  read-create
    STATUS  current
    DESCRIPTION
        "The password for authentication."
    ::= { vrrpNewCfgIfTableEntry 3 }

vrrpNewCfgIfDelete OBJECT-TYPE
    SYNTAX  INTEGER {
        other(1),
        delete(2)
        }
    MAX-ACCESS  read-create
    STATUS  current
    DESCRIPTION
        "When set to the value of 2 (delete), the entire row is deleted.
         When read, other(1) is returned. Setting the value to anything
         other than delete(2) has no effect on the state of the row."
    ::= { vrrpNewCfgIfTableEntry 4 }

-- Failover Virtual Router Groups
vrrpVirtRtrGrpTableMaxSize OBJECT-TYPE
    SYNTAX Integer32
    MAX-ACCESS read-only
    STATUS current
    DESCRIPTION
        "The maximum number of entries in VRRP Group table."
    ::= { vrrpCfg 8 }

vrrpCurCfgVirtRtrGrpTable OBJECT-TYPE
    SYNTAX  SEQUENCE OF VrrpCurCfgVirtRtrGrpTableEntry
    MAX-ACCESS  not-accessible
    STATUS  current
    DESCRIPTION
        "The table of VRRP virtual router group in current_config."
    ::= { vrrpCfg 9 }

vrrpCurCfgVirtRtrGrpTableEntry OBJECT-TYPE
    SYNTAX  VrrpCurCfgVirtRtrGrpTableEntry
    MAX-ACCESS  not-accessible
    STATUS  current
    DESCRIPTION
        "Information about a VRRP failover virtual router."
    INDEX   { vrrpCurCfgVirtRtrGrpIndx }
    ::= { vrrpCurCfgVirtRtrGrpTable 1 }

VrrpCurCfgVirtRtrGrpTableEntry ::= SEQUENCE {
    vrrpCurCfgVirtRtrGrpIndx         Integer32,
    vrrpCurCfgVirtRtrGrpID           INTEGER,
    vrrpCurCfgVirtRtrGrpIfIndex      Integer32,
    vrrpCurCfgVirtRtrGrpInterval     INTEGER,
    vrrpCurCfgVirtRtrGrpPriority     INTEGER,
    vrrpCurCfgVirtRtrGrpPreempt      INTEGER,
    vrrpCurCfgVirtRtrGrpState        INTEGER,
    vrrpCurCfgVirtRtrGrpSharing      INTEGER,
    vrrpCurCfgVirtRtrGrpTckVirtRtr   INTEGER,
    vrrpCurCfgVirtRtrGrpTckIpIntf    INTEGER,
    vrrpCurCfgVirtRtrGrpTckVlanPort  INTEGER,
    vrrpCurCfgVirtRtrGrpTckL4Port    INTEGER,
    vrrpCurCfgVirtRtrGrpTckRServer   INTEGER,
    vrrpCurCfgVirtRtrGrpTckHsrp      INTEGER,
    vrrpCurCfgVirtRtrGrpTckHsrv      INTEGER,
    vrrpCurCfgVirtRtrGrpVersion      INTEGER,
    vrrpCurCfgVirtRtrGrpIpv6Interval INTEGER
    }

vrrpCurCfgVirtRtrGrpIndx OBJECT-TYPE
    SYNTAX  Integer32
    MAX-ACCESS  read-only
    STATUS  current
    DESCRIPTION
        "The VRRP virtual router table index."
    ::= { vrrpCurCfgVirtRtrGrpTableEntry 1 }

vrrpCurCfgVirtRtrGrpID OBJECT-TYPE
    SYNTAX  INTEGER (1..1024)
    MAX-ACCESS  read-only
    STATUS  current
    DESCRIPTION
        "The VRRP virtual router identifier."
    ::= { vrrpCurCfgVirtRtrGrpTableEntry 2 }

vrrpCurCfgVirtRtrGrpIfIndex OBJECT-TYPE
    SYNTAX  Integer32
    MAX-ACCESS  read-only
    STATUS  current
    DESCRIPTION
        "The IfIndex that the VRRP virtual router is representing."
    ::= { vrrpCurCfgVirtRtrGrpTableEntry 3 }

vrrpCurCfgVirtRtrGrpInterval OBJECT-TYPE
    SYNTAX  INTEGER (1..255)
    MAX-ACCESS  read-only
    STATUS  current
    DESCRIPTION
        "The time interval between VRRP advertisements in seconds."
    ::= { vrrpCurCfgVirtRtrGrpTableEntry 4 }

vrrpCurCfgVirtRtrGrpPriority OBJECT-TYPE
    SYNTAX  INTEGER (1..254)
    MAX-ACCESS  read-only
    STATUS  current
    DESCRIPTION
        "The priority value to be used by the specified VRRP virtual routers."
    ::= { vrrpCurCfgVirtRtrGrpTableEntry 5 }

vrrpCurCfgVirtRtrGrpPreempt OBJECT-TYPE
    SYNTAX  INTEGER {
        enabled(1),
        disabled(2)
        }
    MAX-ACCESS  read-only
    STATUS  current
    DESCRIPTION
        "This is for controlling whether a higher priority Backup
         VRRP virtual router preempts a low priority Master.

         enabled(1)  - allow preemption
         disabled(2) - prohibit preemption"
   ::= { vrrpCurCfgVirtRtrGrpTableEntry 6 }

vrrpCurCfgVirtRtrGrpState OBJECT-TYPE
    SYNTAX  INTEGER {
        enabled(1),
        disabled(2)
        }
    MAX-ACCESS  read-only
    STATUS  current
    DESCRIPTION
        "Enable or disable the VRRP virtual router."
    ::= { vrrpCurCfgVirtRtrGrpTableEntry 7 }

vrrpCurCfgVirtRtrGrpSharing OBJECT-TYPE
    SYNTAX  INTEGER {
        enabled(1),
        disabled(2)
        }
    MAX-ACCESS  read-only
    STATUS  current
    DESCRIPTION
        "Enable or disable load sharing of non-master virtual router."
    ::= { vrrpCurCfgVirtRtrGrpTableEntry 8 }

vrrpCurCfgVirtRtrGrpTckVirtRtr OBJECT-TYPE
    SYNTAX  INTEGER {
        enabled(1),
        disabled(2)
        }
    MAX-ACCESS  read-only
    STATUS  current
    DESCRIPTION
        "Enable or disable tracking other virtual routers for
         priority adjustment.  the priority increment is defined
         in vrrpCurCfgGenTckVirtRtrInc."
    ::= { vrrpCurCfgVirtRtrGrpTableEntry 9 }

vrrpCurCfgVirtRtrGrpTckIpIntf OBJECT-TYPE
    SYNTAX  INTEGER {
        enabled(1),
        disabled(2)
        }
    MAX-ACCESS  read-only
    STATUS  current
    DESCRIPTION
        "Enable or disable tracking other router interfaces for
         priority adjustment.  the priority increment is defined
         in vrrpCurCfgGenTckIpIntfInc."
    ::= { vrrpCurCfgVirtRtrGrpTableEntry 10 }

vrrpCurCfgVirtRtrGrpTckVlanPort OBJECT-TYPE
    SYNTAX  INTEGER {
        enabled(1),
        disabled(2)
        }
    MAX-ACCESS  read-only
    STATUS  current
    DESCRIPTION
        "Enable or disable tracking port state of VLAN ports
         for priority adjustment.  the priority increment is
         defined in vrrpCurCfgGenTckVlanPortInc."
    ::= { vrrpCurCfgVirtRtrGrpTableEntry 11 }

vrrpCurCfgVirtRtrGrpTckL4Port OBJECT-TYPE
    SYNTAX  INTEGER {
        enabled(1),
        disabled(2)
        }
    MAX-ACCESS  read-only
    STATUS  current
    DESCRIPTION
        "Enable or disable tracking Layer 4 port states for
         priority adjustment.  the priority increment is defined
         in vrrpCurCfgGenTckL4PortInc.  This is applied when
         virtual server is configured as a VRRP virtual router."
    ::= { vrrpCurCfgVirtRtrGrpTableEntry 12 }

vrrpCurCfgVirtRtrGrpTckRServer OBJECT-TYPE
    SYNTAX  INTEGER {
        enabled(1),
        disabled(2)
        }
    MAX-ACCESS  read-only
    STATUS  current
    DESCRIPTION
        "Enable or disable tracking real server states for
         priority adjustment.  the priority increment is defined
         in vrrpCurCfgGenTckRServerInc.  This is applied when
         virtual server is configured as a VRRP virtual router."
    ::= { vrrpCurCfgVirtRtrGrpTableEntry 13 }

vrrpCurCfgVirtRtrGrpTckHsrp OBJECT-TYPE
    SYNTAX  INTEGER {
        enabled(1),
        disabled(2)
        }
    MAX-ACCESS  read-only
    STATUS  current
    DESCRIPTION
        "Enable or disable tracking HSRP advertisements for
         priority adjustment.  the priority increment is defined
         in vrrpCurCfgGenTckHsrpInc.  This is applied when
         virtual server is configured as a VRRP virtual router."
    ::= { vrrpCurCfgVirtRtrGrpTableEntry 14 }

vrrpCurCfgVirtRtrGrpTckHsrv OBJECT-TYPE
        SYNTAX  INTEGER {
                enabled(1),
                disabled(2)
                }
        MAX-ACCESS  read-only
        STATUS  current
        DESCRIPTION
                "Enable or disable tracking HSRP by VLAN advertisements for
                 priority adjustment.  The priority increment is defined
                 in vrrpCurCfgGenTckHsrvInc.  This is applied when
                 virtual server is configured as a VRRP virtual router."
        ::= { vrrpCurCfgVirtRtrGrpTableEntry 15 }

vrrpCurCfgVirtRtrGrpVersion OBJECT-TYPE
    SYNTAX  INTEGER {
        v4(1),
        v6(2)
    }
    MAX-ACCESS  read-only
    STATUS  current
    DESCRIPTION
        "The VRRP virtual router group IP Version."
    ::= { vrrpCurCfgVirtRtrGrpTableEntry 16 }

vrrpCurCfgVirtRtrGrpIpv6Interval OBJECT-TYPE
    SYNTAX INTEGER (1..4095)
    MAX-ACCESS read-only
    STATUS current
    DESCRIPTION
        "The time interval between IPv6 VRRP advertisements in seconds."
    ::= { vrrpCurCfgVirtRtrGrpTableEntry 17 }

vrrpNewCfgVirtRtrGrpTable OBJECT-TYPE
    SYNTAX  SEQUENCE OF VrrpNewCfgVirtRtrGrpTableEntry
    MAX-ACCESS  not-accessible
    STATUS  current
    DESCRIPTION
        "The table of VRRP virtual router group configuration in new_config."
    ::= { vrrpCfg 10 }

vrrpNewCfgVirtRtrGrpTableEntry OBJECT-TYPE
    SYNTAX  VrrpNewCfgVirtRtrGrpTableEntry
    MAX-ACCESS  not-accessible
    STATUS  current
    DESCRIPTION
        "Information about a VRRP failover virtual router."
    INDEX   { vrrpNewCfgVirtRtrGrpIndx }
    ::= { vrrpNewCfgVirtRtrGrpTable 1 }

VrrpNewCfgVirtRtrGrpTableEntry ::= SEQUENCE {
    vrrpNewCfgVirtRtrGrpIndx         Integer32,
    vrrpNewCfgVirtRtrGrpID           INTEGER,
    vrrpNewCfgVirtRtrGrpIfIndex      Integer32,
    vrrpNewCfgVirtRtrGrpInterval     INTEGER,
    vrrpNewCfgVirtRtrGrpPriority     INTEGER,
    vrrpNewCfgVirtRtrGrpPreempt      INTEGER,
    vrrpNewCfgVirtRtrGrpState        INTEGER,
    vrrpNewCfgVirtRtrGrpDelete       INTEGER,
    vrrpNewCfgVirtRtrGrpSharing      INTEGER,
    vrrpNewCfgVirtRtrGrpTckVirtRtr   INTEGER,
    vrrpNewCfgVirtRtrGrpTckIpIntf    INTEGER,
    vrrpNewCfgVirtRtrGrpTckVlanPort  INTEGER,
    vrrpNewCfgVirtRtrGrpTckL4Port    INTEGER,
    vrrpNewCfgVirtRtrGrpTckRServer   INTEGER,
    vrrpNewCfgVirtRtrGrpTckHsrp      INTEGER,
    vrrpNewCfgVirtRtrGrpTckHsrv      INTEGER,
    vrrpNewCfgVirtRtrGrpVersion      INTEGER,
    vrrpNewCfgVirtRtrGrpIpv6Interval INTEGER
    }

vrrpNewCfgVirtRtrGrpIndx OBJECT-TYPE
    SYNTAX  Integer32
    MAX-ACCESS  read-only
    STATUS  current
    DESCRIPTION
        "The VRRP virtual router table index."
    ::= { vrrpNewCfgVirtRtrGrpTableEntry 1 }

vrrpNewCfgVirtRtrGrpID OBJECT-TYPE
    SYNTAX  INTEGER (1..1024)
    MAX-ACCESS  read-create
    STATUS  current
    DESCRIPTION
        "The VRRP virtual router identifier."
    ::= { vrrpNewCfgVirtRtrGrpTableEntry 2 }

vrrpNewCfgVirtRtrGrpIfIndex OBJECT-TYPE
    SYNTAX  Integer32
    MAX-ACCESS  read-create
    STATUS  current
    DESCRIPTION
        "The IfIndex that the VRRP virtual router is representing."
    ::= { vrrpNewCfgVirtRtrGrpTableEntry 3 }

vrrpNewCfgVirtRtrGrpInterval OBJECT-TYPE
    SYNTAX  INTEGER (1..255)
    MAX-ACCESS  read-create
    STATUS  current
    DESCRIPTION
        "The time interval between VRRP advertisements in seconds."
    ::= { vrrpNewCfgVirtRtrGrpTableEntry 4 }

vrrpNewCfgVirtRtrGrpPriority OBJECT-TYPE
    SYNTAX  INTEGER (1..254)
    MAX-ACCESS  read-create
    STATUS  current
    DESCRIPTION
        "The priority value to be used by the specified VRRP virtual router."
    ::= { vrrpNewCfgVirtRtrGrpTableEntry 5 }

vrrpNewCfgVirtRtrGrpPreempt OBJECT-TYPE
    SYNTAX  INTEGER {
        enabled(1),
        disabled(2)
        }
    MAX-ACCESS  read-create
    STATUS  current
    DESCRIPTION
        "This is for controlling whether a higher priority Backup
         VRRP virtual router preempts a low priority Master.

         enabled(1)  - allow preemption
         disabled(2) - prohibit preemption"
    ::= { vrrpNewCfgVirtRtrGrpTableEntry 6 }

vrrpNewCfgVirtRtrGrpState OBJECT-TYPE
    SYNTAX  INTEGER {
        enabled(1),
        disabled(2)
        }
    MAX-ACCESS  read-create
    STATUS  current
    DESCRIPTION
        "Enable or disable the VRRP virtual router."
    ::= { vrrpNewCfgVirtRtrGrpTableEntry 7 }

vrrpNewCfgVirtRtrGrpDelete OBJECT-TYPE
    SYNTAX  INTEGER {
        other(1),
        delete(2)
        }
    MAX-ACCESS  read-create
    STATUS  current
    DESCRIPTION
        "When set to the value of 2 (delete), the entire row is deleted.
         When read, other(1) is returned. Setting the value to anything
         other than delete(2) has no effect on the state of the row."
    ::= { vrrpNewCfgVirtRtrGrpTableEntry 8 }

vrrpNewCfgVirtRtrGrpSharing OBJECT-TYPE
    SYNTAX  INTEGER {
        enabled(1),
        disabled(2)
        }
    MAX-ACCESS  read-create
    STATUS  current
    DESCRIPTION
        "Enable or disable load sharing of non-master virtual router."
    ::= { vrrpNewCfgVirtRtrGrpTableEntry 9 }

vrrpNewCfgVirtRtrGrpTckVirtRtr OBJECT-TYPE
    SYNTAX  INTEGER {
        enabled(1),
        disabled(2)
        }
    MAX-ACCESS  read-create
    STATUS  current
    DESCRIPTION
        "Enable or disable tracking other virtual routers for
         priority adjustment.  the priority increment is defined
         in vrrpNewCfgGenTckVirtRtrInc."
    ::= { vrrpNewCfgVirtRtrGrpTableEntry 10 }

vrrpNewCfgVirtRtrGrpTckIpIntf OBJECT-TYPE
    SYNTAX  INTEGER {
        enabled(1),
        disabled(2)
        }
    MAX-ACCESS  read-create
    STATUS  current
    DESCRIPTION
        "Enable or disable tracking other router interfaces for
         priority adjustment.  the priority increment is defined
         in vrrpNewCfgGenTckIpIntfInc."
    ::= { vrrpNewCfgVirtRtrGrpTableEntry 11 }

vrrpNewCfgVirtRtrGrpTckVlanPort OBJECT-TYPE
    SYNTAX  INTEGER {
        enabled(1),
        disabled(2)
        }
    MAX-ACCESS  read-create
    STATUS  current
    DESCRIPTION
        "Enable or disable tracking port state of VLAN ports
         for priority adjustment.  the priority increment is
         defined in vrrpNewCfgGenTckVlanPortInc."
    ::= { vrrpNewCfgVirtRtrGrpTableEntry 12 }

vrrpNewCfgVirtRtrGrpTckL4Port OBJECT-TYPE
    SYNTAX  INTEGER {
        enabled(1),
        disabled(2)
        }
    MAX-ACCESS  read-create
    STATUS  current
    DESCRIPTION
        "Enable or disable tracking Layer 4 port states for
         priority adjustment.  the priority increment is defined
         in vrrpNewCfgGenTckL4PortInc.  This is applied when
         virtual server is configured as a VRRP virtual router."
    ::= { vrrpNewCfgVirtRtrGrpTableEntry 13 }

vrrpNewCfgVirtRtrGrpTckRServer OBJECT-TYPE
    SYNTAX  INTEGER {
        enabled(1),
        disabled(2)
        }
    MAX-ACCESS  read-create
    STATUS  current
    DESCRIPTION
        "Enable or disable tracking real server states for
         priority adjustment.  the priority increment is defined
         in vrrpNewCfgGenTckRServerInc.  This is applied when
         virtual server is configured as a VRRP virtual router."
    ::= { vrrpNewCfgVirtRtrGrpTableEntry 14 }

vrrpNewCfgVirtRtrGrpTckHsrp OBJECT-TYPE
    SYNTAX  INTEGER {
        enabled(1),
        disabled(2)
        }
    MAX-ACCESS  read-create
    STATUS  current
    DESCRIPTION
        "Enable or disable tracking HSRP advertisements for
         priority adjustment.  the priority increment is defined
         in vrrpNewCfgGenTckHsrpInc.  This is applied when
         virtual server is configured as a VRRP virtual router."
    ::= { vrrpNewCfgVirtRtrGrpTableEntry 15 }

vrrpNewCfgVirtRtrGrpTckHsrv OBJECT-TYPE
        SYNTAX  INTEGER {
                enabled(1),
                disabled(2)
                }
        MAX-ACCESS  read-create
        STATUS  current
        DESCRIPTION
                "Enable or disable tracking HSRP by VLAN advertisements for
                 priority adjustment.  The priority increment is defined
                 in vrrpNewCfgGenTckHsrvInc.  This is applied when
                 virtual server is configured as a VRRP virtual router."
        ::= { vrrpNewCfgVirtRtrGrpTableEntry 16 }

vrrpNewCfgVirtRtrGrpVersion OBJECT-TYPE
    SYNTAX  INTEGER {
        v4(1),
        v6(2)
    }
    MAX-ACCESS  read-create
    STATUS  current
    DESCRIPTION
        "The VRRP virtual router group IP Version."
    ::= { vrrpNewCfgVirtRtrGrpTableEntry 17 }

vrrpNewCfgVirtRtrGrpIpv6Interval OBJECT-TYPE
    SYNTAX INTEGER (1..4095)
    MAX-ACCESS read-create
    STATUS current
    DESCRIPTION
        "The time interval between IPv6 VRRP advertisements in seconds."
    ::= { vrrpNewCfgVirtRtrGrpTableEntry 18 }

vrrpVirtRtrVrGrpTableMaxSize OBJECT-TYPE
    SYNTAX Integer32
    MAX-ACCESS read-only
    STATUS current
    DESCRIPTION
        "The maximum number of entries in VRRP VrGroup table."
    ::= { vrrpCfg 11 }

vrrpCurCfgVirtRtrVrGrpTable OBJECT-TYPE
    SYNTAX  SEQUENCE OF VrrpCurCfgVirtRtrVrGrpTableEntry
    MAX-ACCESS  not-accessible
    STATUS  current
    DESCRIPTION
        "The table of VRRP virtual router vrgroup configuration in
         the current config."
    ::= { vrrpCfg 12 }

vrrpCurCfgVirtRtrVrGrpTableEntry OBJECT-TYPE
    SYNTAX  VrrpCurCfgVirtRtrVrGrpTableEntry
    MAX-ACCESS  not-accessible
    STATUS  current
    DESCRIPTION
        "Information about setting VRRP virtual router vrgroup."
    INDEX   { vrrpCurCfgVirtRtrVrGrpIndx }
    ::= { vrrpCurCfgVirtRtrVrGrpTable 1 }

VrrpCurCfgVirtRtrVrGrpTableEntry ::= SEQUENCE {
    vrrpCurCfgVirtRtrVrGrpIndx          Integer32,
    vrrpCurCfgVirtRtrVrGrpName          DisplayString,
    vrrpCurCfgVirtRtrVrGrpState         INTEGER,
    vrrpCurCfgVirtRtrVrGrpBmap          OCTET STRING,
    vrrpCurCfgVirtRtrVrGrpPriority      INTEGER,
    vrrpCurCfgVirtRtrVrGrpTckIpIntf     INTEGER,
    vrrpCurCfgVirtRtrVrGrpTckVlanPort   INTEGER,
    vrrpCurCfgVirtRtrVrGrpTckL4Port     INTEGER,
    vrrpCurCfgVirtRtrVrGrpTckRServer    INTEGER,
    vrrpCurCfgVirtRtrVrGrpTckHsrp       INTEGER,
    vrrpCurCfgVirtRtrVrGrpTckHsrv       INTEGER,
    vrrpCurCfgVirtRtrVrGrpTckVirtRtrNo  INTEGER,
    vrrpCurCfgVirtRtrVrGrpAdd           INTEGER,
    vrrpCurCfgVirtRtrVrGrpAdverInterval INTEGER,
    vrrpCurCfgVirtRtrVrGrpPreemption    INTEGER,
    vrrpCurCfgVirtRtrVrGrpSharing       INTEGER
    }

vrrpCurCfgVirtRtrVrGrpIndx OBJECT-TYPE
    SYNTAX  Integer32
    MAX-ACCESS  read-only
    STATUS  current
    DESCRIPTION
        "The VRRP virtual router vrgroup table index."
    ::= { vrrpCurCfgVirtRtrVrGrpTableEntry 1 }

vrrpCurCfgVirtRtrVrGrpName OBJECT-TYPE
    SYNTAX  DisplayString (SIZE(0..8))
    MAX-ACCESS  read-only
    STATUS  current
    DESCRIPTION
        "The VRRP virtual router vrgroup name."
    ::= { vrrpCurCfgVirtRtrVrGrpTableEntry 2 }

vrrpCurCfgVirtRtrVrGrpState OBJECT-TYPE
    SYNTAX  INTEGER {
        enabled(1),
        disabled(2)
    }
    MAX-ACCESS  read-only
    STATUS  current
    DESCRIPTION
        "Enable or disable VRRP Vrgroup state "
    ::= { vrrpCurCfgVirtRtrVrGrpTableEntry 3 }

vrrpCurCfgVirtRtrVrGrpBmap OBJECT-TYPE
    SYNTAX  OCTET STRING
    MAX-ACCESS  read-only
    STATUS  current
    DESCRIPTION
        "The virtual routers added for to this VRRP vrgroup.
         The selected virtual routers are presented in a bitmap format.
         in receiving order:

             OCTET 1  OCTET 2  .....
             xxxxxxxx xxxxxxxx .....
             ||    || |_ Virtual Router 9
             ||    ||
             ||    ||___ Virtual Router 8
             ||    |____ Virtual Router 7
             ||      .    .   .
             ||_________ Virtual Router 2
             |__________ Virtual Router 1

             where x : 1 - The represented Virtual Router is added
                       0 - The represented Virtual Router is not added"
    ::= { vrrpCurCfgVirtRtrVrGrpTableEntry 4 }

vrrpCurCfgVirtRtrVrGrpPriority OBJECT-TYPE
    SYNTAX  INTEGER (1..254)
    MAX-ACCESS  read-only
    STATUS  current
    DESCRIPTION
        "The priority value to be used by the specified VRRP virtual routers."
    ::= { vrrpCurCfgVirtRtrVrGrpTableEntry 5 }

vrrpCurCfgVirtRtrVrGrpTckIpIntf OBJECT-TYPE
    SYNTAX  INTEGER {
        enabled(1),
        disabled(2)
        }
    MAX-ACCESS  read-only
    STATUS  current
    DESCRIPTION
        "Enable or disable tracking interfaces in vrgroup for
         priority adjustment. The priority increment is defined
         in vrrpCurCfgGenTckIpIntfInc."
    ::= { vrrpCurCfgVirtRtrVrGrpTableEntry 6 }

vrrpCurCfgVirtRtrVrGrpTckVlanPort OBJECT-TYPE
    SYNTAX  INTEGER {
        enabled(1),
        disabled(2)
        }
    MAX-ACCESS  read-only
    STATUS  current
    DESCRIPTION
        "Enable or disable tracking port state of VLAN ports
         for priority adjustment. The priority increment is
         defined in vrrpCurCfgGenTckVlanPortInc."
    ::= { vrrpCurCfgVirtRtrVrGrpTableEntry 7 }

vrrpCurCfgVirtRtrVrGrpTckL4Port OBJECT-TYPE
    SYNTAX  INTEGER {
        enabled(1),
        disabled(2)
        }
    MAX-ACCESS  read-only
    STATUS  current
    DESCRIPTION
        "Enable or disable tracking Layer 4 port states for
         priority adjustment.  the priority increment is defined
         in vrrpCurCfgGenTckL4PortInc.  This is applied when
         virtual server is configured as a VRRP virtual router."
    ::= { vrrpCurCfgVirtRtrVrGrpTableEntry 8 }

vrrpCurCfgVirtRtrVrGrpTckRServer OBJECT-TYPE
    SYNTAX  INTEGER {
        enabled(1),
        disabled(2)
        }
    MAX-ACCESS  read-only
    STATUS  current
    DESCRIPTION
        "Enable or disable tracking real server states for
         priority adjustment.  the priority increment is defined
         in vrrpCurCfgGenTckRServerInc.  This is applied when
         virtual server is configured as a VRRP virtual router."
    ::= { vrrpCurCfgVirtRtrVrGrpTableEntry 9 }

vrrpCurCfgVirtRtrVrGrpTckHsrp OBJECT-TYPE
    SYNTAX  INTEGER {
        enabled(1),
        disabled(2)
        }
    MAX-ACCESS  read-only
    STATUS  current
    DESCRIPTION
        "Enable or disable tracking HSRP advertisements for
         priority adjustment.  the priority increment is defined
         in vrrpCurCfgGenTckHsrpInc.  This is applied when
         virtual server is configured as a VRRP virtual router."
    ::= { vrrpCurCfgVirtRtrVrGrpTableEntry 10 }

vrrpCurCfgVirtRtrVrGrpTckHsrv OBJECT-TYPE
        SYNTAX  INTEGER {
                enabled(1),
                disabled(2)
                }
        MAX-ACCESS  read-only
        STATUS  current
        DESCRIPTION
                "Enable or disable tracking HSRP advertisements by VLAN for
                 priority adjustment.  The priority increment is defined
                 in vrrpCurCfgGenTckHsrvInc.  This is applied when
                 virtual server is configured as a VRRP virtual router."
        ::= { vrrpCurCfgVirtRtrVrGrpTableEntry 11 }

vrrpCurCfgVirtRtrVrGrpTckVirtRtrNo OBJECT-TYPE
    SYNTAX  INTEGER (0..1024)
    MAX-ACCESS  read-only
    STATUS  current
    DESCRIPTION
        "The track virtual router for group."
        ::= { vrrpCurCfgVirtRtrVrGrpTableEntry 12 }

vrrpCurCfgVirtRtrVrGrpAdd OBJECT-TYPE
    SYNTAX  INTEGER (0..1024)
    MAX-ACCESS  read-only
    STATUS  current
    DESCRIPTION
        "Specify virtual router number which needs to be added to group."
        ::= { vrrpCurCfgVirtRtrVrGrpTableEntry 13 }

vrrpCurCfgVirtRtrVrGrpAdverInterval OBJECT-TYPE
    SYNTAX  INTEGER (1..255)
    MAX-ACCESS  read-only
    STATUS  current
    DESCRIPTION
        "The advertisement interval for virtual router group."
        ::= { vrrpCurCfgVirtRtrVrGrpTableEntry 14 }


vrrpCurCfgVirtRtrVrGrpPreemption OBJECT-TYPE
    SYNTAX  INTEGER {
            enabled(1),
            disabled(2)
            }
    MAX-ACCESS  read-only
    STATUS  current
    DESCRIPTION
        "Enable/Disable preemption for virtual router group."
        ::= { vrrpCurCfgVirtRtrVrGrpTableEntry 15 }

vrrpCurCfgVirtRtrVrGrpSharing OBJECT-TYPE
    SYNTAX  INTEGER {
            enabled(1),
            disabled(2)
            }
    MAX-ACCESS  read-only
    STATUS  current
    DESCRIPTION
        "Enable/Disable sharing for virtual router group."
        ::= { vrrpCurCfgVirtRtrVrGrpTableEntry 16 }


vrrpNewCfgVirtRtrVrGrpTable OBJECT-TYPE
    SYNTAX  SEQUENCE OF VrrpNewCfgVirtRtrVrGrpTableEntry
    MAX-ACCESS  not-accessible
    STATUS  current
    DESCRIPTION
        "The table of VRRP virtual router vrgroup configuration in new_config."
    ::= { vrrpCfg 13 }

vrrpNewCfgVirtRtrVrGrpTableEntry OBJECT-TYPE
    SYNTAX  VrrpNewCfgVirtRtrVrGrpTableEntry
    MAX-ACCESS  not-accessible
    STATUS  current
    DESCRIPTION
        "Information about setting VRRP virtual router Vrgroup."
    INDEX   { vrrpNewCfgVirtRtrVrGrpIndx }
    ::= { vrrpNewCfgVirtRtrVrGrpTable 1 }

VrrpNewCfgVirtRtrVrGrpTableEntry ::= SEQUENCE {
    vrrpNewCfgVirtRtrVrGrpIndx          Integer32,
    vrrpNewCfgVirtRtrVrGrpName          DisplayString,
    vrrpNewCfgVirtRtrVrGrpAdd           INTEGER,
    vrrpNewCfgVirtRtrVrGrpRem           INTEGER,
    vrrpNewCfgVirtRtrVrGrpState         INTEGER,
    vrrpNewCfgVirtRtrVrGrpDelete        INTEGER,
    vrrpNewCfgVirtRtrVrGrpBmap          OCTET STRING,
    vrrpNewCfgVirtRtrVrGrpPriority      INTEGER,
    vrrpNewCfgVirtRtrVrGrpTckIpIntf     INTEGER,
    vrrpNewCfgVirtRtrVrGrpTckVlanPort   INTEGER,
    vrrpNewCfgVirtRtrVrGrpTckL4Port     INTEGER,
    vrrpNewCfgVirtRtrVrGrpTckRServer    INTEGER,
    vrrpNewCfgVirtRtrVrGrpTckHsrp       INTEGER,
    vrrpNewCfgVirtRtrVrGrpTckHsrv       INTEGER,
    vrrpNewCfgVirtRtrVrGrpTckVirtRtrNo  INTEGER,
    vrrpNewCfgVirtRtrVrGrpAdverInterval INTEGER,
    vrrpNewCfgVirtRtrVrGrpPreemption    INTEGER,
    vrrpNewCfgVirtRtrVrGrpSharing       INTEGER
    }

vrrpNewCfgVirtRtrVrGrpIndx OBJECT-TYPE
    SYNTAX  Integer32
    MAX-ACCESS  read-only
    STATUS  current
    DESCRIPTION
        "The VRRP virtual router vrgroup table index."
    ::= { vrrpNewCfgVirtRtrVrGrpTableEntry 1 }

vrrpNewCfgVirtRtrVrGrpName OBJECT-TYPE
    SYNTAX  DisplayString (SIZE(0..8))
    MAX-ACCESS  read-create
    STATUS  current
    DESCRIPTION
        "The VRRP virtual router vrgroup name."
    ::= { vrrpNewCfgVirtRtrVrGrpTableEntry 2 }

vrrpNewCfgVirtRtrVrGrpAdd OBJECT-TYPE
    SYNTAX  INTEGER (1..1024)
    MAX-ACCESS  read-create
    STATUS  current
    DESCRIPTION
        "The VRRP virtual router to be added to this vrgroup table."
    ::= { vrrpNewCfgVirtRtrVrGrpTableEntry 3 }

vrrpNewCfgVirtRtrVrGrpRem OBJECT-TYPE
    SYNTAX  INTEGER (1..1024)
    MAX-ACCESS  read-create
    STATUS  current
    DESCRIPTION
        "The VRRP virtual router to be removed from this vrgroup table."
    ::= { vrrpNewCfgVirtRtrVrGrpTableEntry 4 }

vrrpNewCfgVirtRtrVrGrpState OBJECT-TYPE
        SYNTAX  INTEGER {
                enabled(1),
                disabled(2)
                }
        MAX-ACCESS  read-create
        STATUS  current
        DESCRIPTION
                "Enable or disable VRRP Vrgroup state "
        ::= { vrrpNewCfgVirtRtrVrGrpTableEntry 5 }

vrrpNewCfgVirtRtrVrGrpDelete OBJECT-TYPE
    SYNTAX  INTEGER {
        other(1),
        delete(2)
        }
    MAX-ACCESS  read-create
    STATUS  current
    DESCRIPTION
        "When set to the value of 2 (delete), the entire row is deleted.
         When read, other(1) is returned. Setting the value to anything
         other than 2(delete) has no effect on the state of the row."
    ::= { vrrpNewCfgVirtRtrVrGrpTableEntry 6 }

vrrpNewCfgVirtRtrVrGrpBmap OBJECT-TYPE
    SYNTAX  OCTET STRING
    MAX-ACCESS  read-only
    STATUS  current
    DESCRIPTION
        "The virtual routers added to this VRRP vrgroup.
         The selected virtual routers are presented in a bitmap format.
         in receiving order:

             OCTET 1  OCTET 2  .....
             xxxxxxxx xxxxxxxx .....
             ||    || |_ Virtual Router 9
             ||    ||
             ||    ||___ Virtual Router 8
             ||    |____ Virtual Router 7
             ||      .    .   .
             ||_________ Virtual Router 2
             |__________ Virtual Router 1

             where x : 1 - The represented Virtual Router is added
                       0 - The represented Virtual Router is not added"
    ::= { vrrpNewCfgVirtRtrVrGrpTableEntry 7 }

vrrpNewCfgVirtRtrVrGrpPriority OBJECT-TYPE
    SYNTAX  INTEGER (1..254)
    MAX-ACCESS  read-create
    STATUS  current
    DESCRIPTION
        "The priority value to be used by the specified VRRP virtual routers."
    ::= { vrrpNewCfgVirtRtrVrGrpTableEntry 8 }

vrrpNewCfgVirtRtrVrGrpTckIpIntf OBJECT-TYPE
    SYNTAX  INTEGER {
        enabled(1),
        disabled(2)
        }
    MAX-ACCESS  read-create
    STATUS  current
    DESCRIPTION
        "Enable or disable tracking interfaces in vrgroup for
         priority adjustment. The priority increment is defined
         in vrrpCurCfgGenTckIpIntfInc."
    ::= { vrrpNewCfgVirtRtrVrGrpTableEntry 9 }

vrrpNewCfgVirtRtrVrGrpTckVlanPort OBJECT-TYPE
    SYNTAX  INTEGER {
        enabled(1),
        disabled(2)
        }
    MAX-ACCESS  read-create
    STATUS  current
    DESCRIPTION
        "Enable or disable tracking port state of VLAN ports
         for priority adjustment. The priority increment is
         defined in vrrpCurCfgGenTckVlanPortInc."
    ::= { vrrpNewCfgVirtRtrVrGrpTableEntry 10 }

vrrpNewCfgVirtRtrVrGrpTckL4Port OBJECT-TYPE
    SYNTAX  INTEGER {
        enabled(1),
        disabled(2)
        }
    MAX-ACCESS  read-create
    STATUS  current
    DESCRIPTION
        "Enable or disable tracking Layer 4 port states for
         priority adjustment.  the priority increment is defined
         in vrrpCurCfgGenTckL4PortInc.  This is applied when
         virtual server is configured as a VRRP virtual router."
    ::= { vrrpNewCfgVirtRtrVrGrpTableEntry 11 }

vrrpNewCfgVirtRtrVrGrpTckRServer OBJECT-TYPE
    SYNTAX  INTEGER {
        enabled(1),
        disabled(2)
        }
    MAX-ACCESS  read-create
    STATUS  current
    DESCRIPTION
        "Enable or disable tracking real server states for
         priority adjustment.  the priority increment is defined
         in vrrpCurCfgGenTckRServerInc.  This is applied when
         virtual server is configured as a VRRP virtual router."
    ::= { vrrpNewCfgVirtRtrVrGrpTableEntry 12 }

vrrpNewCfgVirtRtrVrGrpTckHsrp OBJECT-TYPE
    SYNTAX  INTEGER {
        enabled(1),
        disabled(2)
        }
    MAX-ACCESS  read-create
    STATUS  current
    DESCRIPTION
        "Enable or disable tracking HSRP advertisements for
         priority adjustment.  the priority increment is defined
         in vrrpCurCfgGenTckHsrpInc.  This is applied when
         virtual server is configured as a VRRP virtual router."
    ::= { vrrpNewCfgVirtRtrVrGrpTableEntry 13 }

vrrpNewCfgVirtRtrVrGrpTckHsrv OBJECT-TYPE
        SYNTAX  INTEGER {
                enabled(1),
                disabled(2)
                }
        MAX-ACCESS  read-create
        STATUS  current
        DESCRIPTION
                "Enable or disable tracking HSRP advertisements by VLAN for
                 priority adjustment.  The priority increment is defined
                 in vrrpCurCfgGenTckHsrvInc.  This is applied when
                 virtual server is configured as a VRRP virtual router."
        ::= { vrrpNewCfgVirtRtrVrGrpTableEntry 14 }

vrrpNewCfgVirtRtrVrGrpTckVirtRtrNo OBJECT-TYPE
    SYNTAX  INTEGER (0..1024)
    MAX-ACCESS  read-create
    STATUS  current
    DESCRIPTION
        "The track virtual router for group."
        ::= { vrrpNewCfgVirtRtrVrGrpTableEntry 15 }


vrrpNewCfgVirtRtrVrGrpAdverInterval OBJECT-TYPE
    SYNTAX  INTEGER (1..255)
    MAX-ACCESS  read-create
    STATUS  current
    DESCRIPTION
        "The advertisement interval for virtual router group."
        ::= { vrrpNewCfgVirtRtrVrGrpTableEntry 16 }


vrrpNewCfgVirtRtrVrGrpPreemption OBJECT-TYPE
    SYNTAX  INTEGER {
            enabled(1),
            disabled(2)
            }
    MAX-ACCESS  read-create
    STATUS  current
    DESCRIPTION
        "Enable/Disable preemption for virtual router group."
        ::= { vrrpNewCfgVirtRtrVrGrpTableEntry 17 }

vrrpNewCfgVirtRtrVrGrpSharing OBJECT-TYPE
    SYNTAX  INTEGER {
            enabled(1),
            disabled(2)
            }
    MAX-ACCESS  read-create
    STATUS  current
    DESCRIPTION
        "Enable/Disable sharing for virtual router group."
        ::= { vrrpNewCfgVirtRtrVrGrpTableEntry 18 }



-- Domain Name Server Configuration

dnsCurCfgPrimaryIpAddr OBJECT-TYPE
    SYNTAX  IpAddress
    MAX-ACCESS  read-only
    STATUS  current
    DESCRIPTION
        "The DNS primary IP address in the current_configuration block."
    ::= { dnsCfg 1 }

dnsNewCfgPrimaryIpAddr OBJECT-TYPE
    SYNTAX  IpAddress
    MAX-ACCESS  read-write
    STATUS  current
    DESCRIPTION
        "The DNS primary IP address in the new_configuration block."
    ::= { dnsCfg 2 }

dnsCurCfgSecondaryIpAddr OBJECT-TYPE
    SYNTAX  IpAddress
    MAX-ACCESS  read-only
    STATUS  current
    DESCRIPTION
        "The DNS secondary IP address in the current_configuration block."
    ::= { dnsCfg 3 }

dnsNewCfgSecondaryIpAddr OBJECT-TYPE
    SYNTAX  IpAddress
    MAX-ACCESS  read-write
    STATUS  current
    DESCRIPTION
        "The DNS secondary IP address in the new_configuration block."
    ::= { dnsCfg 4 }

dnsCurCfgDomainName OBJECT-TYPE
    SYNTAX  DisplayString (SIZE(0..191))
    MAX-ACCESS  read-only
    STATUS  current
    DESCRIPTION
        "The DNS doamin name in the current_configuration block."
    ::= { dnsCfg 5 }

dnsNewCfgDomainName OBJECT-TYPE
    SYNTAX  DisplayString (SIZE(0..191))
    MAX-ACCESS  read-write
    STATUS  current
    DESCRIPTION
        "The DNS doamin name in the new_configuration block."
    ::= { dnsCfg 6 }

dnsCurCfgPrimaryIpv6Addr OBJECT-TYPE
    SYNTAX DisplayString (SIZE(0..40))
    MAX-ACCESS  read-only
    STATUS  current
    DESCRIPTION
        "The DNS primary IPv6 address in the current_configuration block."
    ::= { dnsCfg 7 }

dnsNewCfgPrimaryIpv6Addr OBJECT-TYPE
    SYNTAX DisplayString (SIZE(0..40))
    MAX-ACCESS  read-write
    STATUS  current
    DESCRIPTION
        "The DNS primary IPv6 address in the new_configuration block."
    ::= { dnsCfg 8 }

dnsCurCfgSecondaryIpv6Addr OBJECT-TYPE
    SYNTAX DisplayString (SIZE(0..40))
    MAX-ACCESS  read-only
    STATUS  current
    DESCRIPTION
        "The DNS secondary IPv6 address in the current_configuration block."
    ::= { dnsCfg 9 }

dnsNewCfgSecondaryIpv6Addr OBJECT-TYPE
    SYNTAX DisplayString (SIZE(0..40))
    MAX-ACCESS  read-write
    STATUS  current
    DESCRIPTION
        "The DNS secondary IPv6 address in the new_configuration block."
    ::= { dnsCfg 10 }


--
-- IP network filter configuration
--
ipNwfTableMax OBJECT-TYPE
    SYNTAX Integer32
    MAX-ACCESS read-only
    STATUS current
    DESCRIPTION
	"The maximum number of rows in the IP network filter table."
    ::= { ipNwfCfg 1 }

ipCurCfgNwfTable OBJECT-TYPE
    SYNTAX SEQUENCE OF IpCurCfgNwfEntry
    MAX-ACCESS not-accessible
    STATUS current
    DESCRIPTION
      "The table of IP network filter configuration in the current_config."
    ::= { ipNwfCfg 2 }

ipCurCfgNwfEntry OBJECT-TYPE
    SYNTAX IpCurCfgNwfEntry
    MAX-ACCESS not-accessible
    STATUS current
    DESCRIPTION
      "Information about an IP network filter."
    INDEX { ipCurCfgNwfIndex }
    ::= { ipCurCfgNwfTable 1 }

IpCurCfgNwfEntry ::= SEQUENCE {
    ipCurCfgNwfIndex     Integer32,
    ipCurCfgNwfAddr      IpAddress,
    ipCurCfgNwfMask      IpAddress,
    ipCurCfgNwfState     INTEGER
    }

ipCurCfgNwfIndex OBJECT-TYPE
    SYNTAX Integer32
    MAX-ACCESS read-only
    STATUS current
    DESCRIPTION
	"The network filter number for which the NWF is related."
    ::= { ipCurCfgNwfEntry 1}

ipCurCfgNwfAddr OBJECT-TYPE
    SYNTAX IpAddress
    MAX-ACCESS read-only
    STATUS current
    DESCRIPTION
	"The IP address of the network filter."
    ::= { ipCurCfgNwfEntry 2 }

ipCurCfgNwfMask OBJECT-TYPE
    SYNTAX IpAddress
    MAX-ACCESS read-only
    STATUS current
    DESCRIPTION
	"The subnet mask of the network filter."
    ::= { ipCurCfgNwfEntry 3 }

ipCurCfgNwfState OBJECT-TYPE
    SYNTAX INTEGER {
        enabled(1),
        disabled(2)
	}
    MAX-ACCESS  read-only
    STATUS  current
    DESCRIPTION
	"Enable or disable the network filter."
    ::= { ipCurCfgNwfEntry 4 }

ipNewCfgNwfTable OBJECT-TYPE
    SYNTAX SEQUENCE OF IpNewCfgNwfEntry
    MAX-ACCESS not-accessible
    STATUS current
    DESCRIPTION
      "The table of IP network filter configuration in the current_config."
    ::= { ipNwfCfg 3 }

ipNewCfgNwfEntry OBJECT-TYPE
    SYNTAX IpNewCfgNwfEntry
    MAX-ACCESS not-accessible
    STATUS current
    DESCRIPTION
      "Information about an IP network filter."
    INDEX { ipNewCfgNwfIndex }
    ::= { ipNewCfgNwfTable 1 }

IpNewCfgNwfEntry ::= SEQUENCE {
    ipNewCfgNwfIndex     Integer32,
    ipNewCfgNwfAddr      IpAddress,
    ipNewCfgNwfMask      IpAddress,
    ipNewCfgNwfState     INTEGER,
    ipNewCfgNwfDelete    INTEGER
    }

ipNewCfgNwfIndex OBJECT-TYPE
    SYNTAX Integer32
    MAX-ACCESS read-only
    STATUS current
    DESCRIPTION
	"The network filter number for which the NWF is related."
    ::= { ipNewCfgNwfEntry 1}

ipNewCfgNwfAddr OBJECT-TYPE
    SYNTAX IpAddress
    MAX-ACCESS read-create
    STATUS current
    DESCRIPTION
	"The IP address of the network filter."
    ::= { ipNewCfgNwfEntry 2 }

ipNewCfgNwfMask OBJECT-TYPE
    SYNTAX IpAddress
    MAX-ACCESS read-create
    STATUS current
    DESCRIPTION
	"The subnet mask of the network filter."
    ::= { ipNewCfgNwfEntry 3 }

ipNewCfgNwfState OBJECT-TYPE
    SYNTAX INTEGER {
        enabled(1),
        disabled(2)
	}
    MAX-ACCESS  read-create
    STATUS  current
    DESCRIPTION
	"Enable or disable the network filter."
    ::= { ipNewCfgNwfEntry 4 }

ipNewCfgNwfDelete OBJECT-TYPE
    SYNTAX INTEGER {
        other(1),
        delete(2)
        }
    MAX-ACCESS read-create
    STATUS current
    DESCRIPTION
	"When set to the value of 2 (delete), the entire row is deleted.
	 When read, other(1) is returned. Setting the value to anything
	 other than 2(delete) has no effect on the state of the row."
    ::= { ipNewCfgNwfEntry 5 }

--
-- IP route map configuration
--
ipRmapTableMax OBJECT-TYPE
    SYNTAX Integer32
    MAX-ACCESS read-only
    STATUS current
    DESCRIPTION
	"The maximum number of rows in the IP route map table."
    ::= { ipRmapCfg 1 }

ipCurCfgRmapTable OBJECT-TYPE
    SYNTAX SEQUENCE OF IpCurCfgRmapEntry
    MAX-ACCESS not-accessible
    STATUS current
    DESCRIPTION
      "The table of IP route map configuration in the current_config."
    ::= { ipRmapCfg 2 }

ipCurCfgRmapEntry OBJECT-TYPE
    SYNTAX IpCurCfgRmapEntry
    MAX-ACCESS not-accessible
    STATUS current
    DESCRIPTION
      "Information about an IP route map."
    INDEX { ipCurCfgRmapIndex }
    ::= { ipCurCfgRmapTable 1 }

IpCurCfgRmapEntry ::= SEQUENCE {
    ipCurCfgRmapIndex		Integer32,
    ipCurCfgRmapLp	  	Unsigned32,
    ipCurCfgRmapMetric	  	Unsigned32,
    ipCurCfgRmapPrec	  	INTEGER,
    ipCurCfgRmapWeight	 	INTEGER,
    ipCurCfgRmapState     	INTEGER,
    ipCurCfgRmapMetricType	INTEGER,
    ipCurCfgRmapAp		DisplayString
    }

ipCurCfgRmapIndex OBJECT-TYPE
    SYNTAX Integer32
    MAX-ACCESS read-only
    STATUS current
    DESCRIPTION
	"The route map number for which the RMAP is related."
    ::= { ipCurCfgRmapEntry 1}

ipCurCfgRmapLp OBJECT-TYPE
    SYNTAX Unsigned32 (0..4294967295)
    MAX-ACCESS read-only
    STATUS current
    DESCRIPTION
	"The local-preference of the route map. 4294967295 means none"
    ::= { ipCurCfgRmapEntry 2 }

ipCurCfgRmapMetric OBJECT-TYPE
    SYNTAX Unsigned32 (0..4294967295)
    MAX-ACCESS read-only
    STATUS current
    DESCRIPTION
	"The metric of the route map. 4294967295 means none"
    ::= { ipCurCfgRmapEntry 3 }

ipCurCfgRmapPrec OBJECT-TYPE
    SYNTAX INTEGER (1..255)
    MAX-ACCESS read-only
    STATUS current
    DESCRIPTION
	"The precedence of the route map."
    ::= { ipCurCfgRmapEntry 4 }

ipCurCfgRmapWeight OBJECT-TYPE
    SYNTAX INTEGER (0..65535)
    MAX-ACCESS read-only
    STATUS current
    DESCRIPTION
	"The weight of the route map. 65535 means none"
    ::= { ipCurCfgRmapEntry 5 }

ipCurCfgRmapState OBJECT-TYPE
    SYNTAX INTEGER {
        enabled(1),
        disabled(2)
	}
    MAX-ACCESS  read-only
    STATUS  current
    DESCRIPTION
	"Enable or disable the route map."
    ::= { ipCurCfgRmapEntry 6 }

ipCurCfgRmapAp OBJECT-TYPE
    SYNTAX DisplayString (SIZE(0..18))
    MAX-ACCESS read-only
    STATUS current
    DESCRIPTION
	"The as-path prepend of the matched route. Up to 3 AS number can be
	 displayed for the string.
	 The usuage is:<AS number> [<AS number>][ <AS number>]"
    ::= { ipCurCfgRmapEntry 7 }

ipCurCfgRmapMetricType OBJECT-TYPE
    SYNTAX INTEGER {
        none(1),
        type1(2),
        type2(3)
        }
    MAX-ACCESS  read-only
    STATUS  current
    DESCRIPTION
	"The OSPF metric-type of the matched route."
    ::= { ipCurCfgRmapEntry 8 }

ipNewCfgRmapTable OBJECT-TYPE
    SYNTAX SEQUENCE OF IpNewCfgRmapEntry
    MAX-ACCESS not-accessible
    STATUS current
    DESCRIPTION
      "The table of IP route map configuration in the current_config."
    ::= { ipRmapCfg 3 }

ipNewCfgRmapEntry OBJECT-TYPE
    SYNTAX IpNewCfgRmapEntry
    MAX-ACCESS not-accessible
    STATUS current
    DESCRIPTION
      "Information about an IP route map."
    INDEX { ipNewCfgRmapIndex }
    ::= { ipNewCfgRmapTable 1 }

IpNewCfgRmapEntry ::= SEQUENCE {
    ipNewCfgRmapIndex		Integer32,
    ipNewCfgRmapLp	  	Unsigned32,
    ipNewCfgRmapMetric	  	Unsigned32,
    ipNewCfgRmapPrec	  	INTEGER,
    ipNewCfgRmapWeight	 	INTEGER,
    ipNewCfgRmapState     	INTEGER,
    ipNewCfgRmapAp		DisplayString,
    ipNewCfgRmapMetricType	INTEGER,
    ipNewCfgRmapDelete		INTEGER
    }

ipNewCfgRmapIndex OBJECT-TYPE
    SYNTAX Integer32
    MAX-ACCESS read-only
    STATUS current
    DESCRIPTION
	"The route map number for which the RMAP is related."
    ::= { ipNewCfgRmapEntry 1}

ipNewCfgRmapLp OBJECT-TYPE
    SYNTAX Unsigned32 (0..4294967295)
    MAX-ACCESS read-create
    STATUS current
    DESCRIPTION
	"The local-preference of the route map. 4294967295 means none"
    ::= { ipNewCfgRmapEntry 2 }

ipNewCfgRmapMetric OBJECT-TYPE
    SYNTAX Unsigned32 (0..4294967295)
    MAX-ACCESS read-create
    STATUS current
    DESCRIPTION
	"The metric of the route map. 4294967295 means none"
    ::= { ipNewCfgRmapEntry 3 }

ipNewCfgRmapPrec OBJECT-TYPE
    SYNTAX INTEGER (1..255)
    MAX-ACCESS read-create
    STATUS current
    DESCRIPTION
	"The precedence of the route map."
    ::= { ipNewCfgRmapEntry 4 }

ipNewCfgRmapWeight OBJECT-TYPE
    SYNTAX INTEGER (0..65535)
    MAX-ACCESS read-create
    STATUS current
    DESCRIPTION
	"The weight of the route map. 65535 means none"
    ::= { ipNewCfgRmapEntry 5 }

ipNewCfgRmapState OBJECT-TYPE
    SYNTAX INTEGER {
        enabled(1),
        disabled(2)
	}
    MAX-ACCESS  read-create
    STATUS  current
    DESCRIPTION
	"Enable or disable the route map."
    ::= { ipNewCfgRmapEntry 6 }

ipNewCfgRmapAp OBJECT-TYPE
    SYNTAX DisplayString (SIZE(0..18))
    MAX-ACCESS read-create
    STATUS current
    DESCRIPTION
	"The as-path prepend of the matched route. Up to 3 AS number can be
	 displayed for the string.
	 The usuage is:<AS number> [<AS number>][ <AS number>]"
    ::= { ipNewCfgRmapEntry 7 }

ipNewCfgRmapMetricType OBJECT-TYPE
    SYNTAX INTEGER {
        none(1),
        type1(2),
        type2(3)
        }
    MAX-ACCESS  read-create
    STATUS  current
    DESCRIPTION
	"The OSPF metric-type of the matched route."
    ::= { ipNewCfgRmapEntry 8 }

ipNewCfgRmapDelete OBJECT-TYPE
    SYNTAX  INTEGER {
	other(1),
	delete(2)
	}
    MAX-ACCESS  read-create
    STATUS  current
    DESCRIPTION
	"When set to the value of 2 (delete), the entire row is deleted.
	 When read, other(1) is returned. Setting the value to anything
	 other than 2(delete) has no effect on the state of the row."
    ::= { ipNewCfgRmapEntry 9 }

ipAlistTableMax OBJECT-TYPE
    SYNTAX Integer32
    MAX-ACCESS read-only
    STATUS current
    DESCRIPTION
	"The maximum number of rows in the IP route map table."
    ::= { ipRmapCfg 4 }

ipCurCfgAlistTable OBJECT-TYPE
    SYNTAX SEQUENCE OF IpCurCfgAlistEntry
    MAX-ACCESS not-accessible
    STATUS current
    DESCRIPTION
      "The table of IP route map access list configuration in the
       current_config."
    ::= { ipRmapCfg 5 }

ipCurCfgAlistEntry OBJECT-TYPE
    SYNTAX IpCurCfgAlistEntry
    MAX-ACCESS not-accessible
    STATUS current
    DESCRIPTION
      "Information about an IP route map."
    INDEX { ipCurCfgAlistRmapIndex, ipCurCfgAlistIndex }
    ::= { ipCurCfgAlistTable 1 }

IpCurCfgAlistEntry ::= SEQUENCE {
    ipCurCfgAlistRmapIndex	Integer32,
    ipCurCfgAlistIndex		Integer32,
    ipCurCfgAlistNwf		INTEGER,
    ipCurCfgAlistMetric	  	Unsigned32,
    ipCurCfgAlistAction		INTEGER,
    ipCurCfgAlistState     	INTEGER
    }

ipCurCfgAlistRmapIndex OBJECT-TYPE
    SYNTAX Integer32
    MAX-ACCESS read-only
    STATUS current
    DESCRIPTION
	"The route map number for which the RMAP is related."
    ::= { ipCurCfgAlistEntry 1 }

ipCurCfgAlistIndex OBJECT-TYPE
    SYNTAX Integer32
    MAX-ACCESS read-only
    STATUS current
    DESCRIPTION
	"The access list number for which the access list is related."
    ::= { ipCurCfgAlistEntry 2 }

ipCurCfgAlistNwf OBJECT-TYPE
    SYNTAX INTEGER (0..256)
    MAX-ACCESS read-only
    STATUS current
    DESCRIPTION
	"The network filter number of the route map access list.
	 0 means none"
    ::= { ipCurCfgAlistEntry 3 }

ipCurCfgAlistMetric OBJECT-TYPE
    SYNTAX Unsigned32 (0..4294967295)
    MAX-ACCESS read-only
    STATUS current
    DESCRIPTION
	"The metric of the route map access list. 4294967295 means none"
    ::= { ipCurCfgAlistEntry 4 }

ipCurCfgAlistAction OBJECT-TYPE
    SYNTAX INTEGER {
	permit(1),
	deny(2)
	}
    MAX-ACCESS read-only
    STATUS current
    DESCRIPTION
	"Action of the route map access list."
    ::= { ipCurCfgAlistEntry 5 }

ipCurCfgAlistState OBJECT-TYPE
    SYNTAX INTEGER {
        enabled(1),
        disabled(2)
	}
    MAX-ACCESS  read-only
    STATUS  current
    DESCRIPTION
	"Enable or disable the route map access list."
    ::= { ipCurCfgAlistEntry 6 }

ipNewCfgAlistTable OBJECT-TYPE
    SYNTAX SEQUENCE OF IpNewCfgAlistEntry
    MAX-ACCESS not-accessible
    STATUS current
    DESCRIPTION
      "The table of IP route map access list configuration in the
       current_config."
    ::= { ipRmapCfg 6 }

ipNewCfgAlistEntry OBJECT-TYPE
    SYNTAX IpNewCfgAlistEntry
    MAX-ACCESS not-accessible
    STATUS current
    DESCRIPTION
      "Information about an IP route map."
    INDEX { ipNewCfgAlistRmapIndex, ipNewCfgAlistIndex }
    ::= { ipNewCfgAlistTable 1 }

IpNewCfgAlistEntry ::= SEQUENCE {
    ipNewCfgAlistRmapIndex	Integer32,
    ipNewCfgAlistIndex		Integer32,
    ipNewCfgAlistNwf		INTEGER,
    ipNewCfgAlistMetric	  	Unsigned32,
    ipNewCfgAlistAction		INTEGER,
    ipNewCfgAlistState     	INTEGER,
    ipNewCfgAlistDelete		INTEGER
    }

ipNewCfgAlistRmapIndex OBJECT-TYPE
    SYNTAX Integer32
    MAX-ACCESS read-only
    STATUS current
    DESCRIPTION
	"The route map number for which the RMAP is related."
    ::= { ipNewCfgAlistEntry 1 }

ipNewCfgAlistIndex OBJECT-TYPE
    SYNTAX Integer32
    MAX-ACCESS read-only
    STATUS current
    DESCRIPTION
	"The access list number for which the access list is related."
    ::= { ipNewCfgAlistEntry 2 }

ipNewCfgAlistNwf OBJECT-TYPE
    SYNTAX INTEGER (0..256)
    MAX-ACCESS read-create
    STATUS current
    DESCRIPTION
	"The network filter number of the route map access list.
	 0 means none"
    ::= { ipNewCfgAlistEntry 3 }

ipNewCfgAlistMetric OBJECT-TYPE
    SYNTAX Unsigned32 (0..4294967295)
    MAX-ACCESS read-create
    STATUS current
    DESCRIPTION
	"The metric of the route map access list. 4294967295 means none"
    ::= { ipNewCfgAlistEntry 4 }

ipNewCfgAlistAction OBJECT-TYPE
    SYNTAX INTEGER {
	permit(1),
	deny(2)
	}
    MAX-ACCESS read-create
    STATUS current
    DESCRIPTION
	"Action of the route map access list."
    ::= { ipNewCfgAlistEntry 5 }

ipNewCfgAlistState OBJECT-TYPE
    SYNTAX INTEGER {
        enabled(1),
        disabled(2)
	}
    MAX-ACCESS  read-create
    STATUS  current
    DESCRIPTION
	"Enable or disable the route map access list."
    ::= { ipNewCfgAlistEntry 6 }

ipNewCfgAlistDelete OBJECT-TYPE
    SYNTAX  INTEGER {
	other(1),
	delete(2)
	}
    MAX-ACCESS  read-create
    STATUS  current
    DESCRIPTION
	"When set to the value of 2 (delete), the entire row is deleted.
	 When read, other(1) is returned. Setting the value to anything
	 other than 2(delete) has no effect on the state of the row."
    ::= { ipNewCfgAlistEntry 7 }

ipAspathTableMax OBJECT-TYPE
    SYNTAX Integer32
    MAX-ACCESS read-only
    STATUS current
    DESCRIPTION
	"The maximum number of rows in the IP route map table."
    ::= { ipRmapCfg 7 }

ipCurCfgAspathTable OBJECT-TYPE
    SYNTAX SEQUENCE OF IpCurCfgAspathEntry
    MAX-ACCESS not-accessible
    STATUS current
    DESCRIPTION
      "The table of IP route map access path configuration."
    ::= { ipRmapCfg 8 }

ipCurCfgAspathEntry OBJECT-TYPE
    SYNTAX IpCurCfgAspathEntry
    MAX-ACCESS not-accessible
    STATUS current
    DESCRIPTION
      "Information about an IP route map."
    INDEX { ipCurCfgAspathRmapIndex, ipCurCfgAlistIndex }
    ::= { ipCurCfgAspathTable 1 }

IpCurCfgAspathEntry ::= SEQUENCE {
    ipCurCfgAspathRmapIndex	Integer32,
    ipCurCfgAspathIndex		Integer32,
    ipCurCfgAspathAS		INTEGER,
    ipCurCfgAspathAction	INTEGER,
    ipCurCfgAspathState     	INTEGER
    }

ipCurCfgAspathRmapIndex OBJECT-TYPE
    SYNTAX Integer32
    MAX-ACCESS read-only
    STATUS current
    DESCRIPTION
	"The route map number for which the RMAP is related."
    ::= { ipCurCfgAspathEntry 1 }

ipCurCfgAspathIndex OBJECT-TYPE
    SYNTAX Integer32
    MAX-ACCESS read-only
    STATUS current
    DESCRIPTION
	"The access path number for which the access list is related."
    ::= { ipCurCfgAspathEntry 2 }

ipCurCfgAspathAS OBJECT-TYPE
    SYNTAX INTEGER (0..65535)
    MAX-ACCESS read-only
    STATUS current
    DESCRIPTION
	"The AS number of the route map access path.
	 0 means none"
    ::= { ipCurCfgAspathEntry 3 }

ipCurCfgAspathAction OBJECT-TYPE
    SYNTAX INTEGER {
	permit(1),
	deny(2)
	}
    MAX-ACCESS read-only
    STATUS current
    DESCRIPTION
	"Action of the route map access path."
    ::= { ipCurCfgAspathEntry 4 }

ipCurCfgAspathState OBJECT-TYPE
    SYNTAX INTEGER {
        enabled(1),
        disabled(2)
	}
    MAX-ACCESS  read-only
    STATUS  current
    DESCRIPTION
	"Enable or disable the route map access path."
    ::= { ipCurCfgAspathEntry 5 }

ipNewCfgAspathTable OBJECT-TYPE
    SYNTAX SEQUENCE OF IpNewCfgAspathEntry
    MAX-ACCESS not-accessible
    STATUS current
    DESCRIPTION
      "The table of IP route map access path configuration"
    ::= { ipRmapCfg 9 }

ipNewCfgAspathEntry OBJECT-TYPE
    SYNTAX IpNewCfgAspathEntry
    MAX-ACCESS not-accessible
    STATUS current
    DESCRIPTION
      "Information about an IP route map."
    INDEX { ipNewCfgAspathRmapIndex, ipNewCfgAspathIndex }
    ::= { ipNewCfgAspathTable 1 }

IpNewCfgAspathEntry ::= SEQUENCE {
    ipNewCfgAspathRmapIndex	Integer32,
    ipNewCfgAspathIndex		Integer32,
    ipNewCfgAspathAS		INTEGER,
    ipNewCfgAspathAction	INTEGER,
    ipNewCfgAspathState     	INTEGER,
    ipNewCfgAspathDelete	INTEGER
    }

ipNewCfgAspathRmapIndex OBJECT-TYPE
    SYNTAX Integer32
    MAX-ACCESS read-only
    STATUS current
    DESCRIPTION
	"The route map number for which the RMAP is related."
    ::= { ipNewCfgAspathEntry 1 }

ipNewCfgAspathIndex OBJECT-TYPE
    SYNTAX Integer32
    MAX-ACCESS read-only
    STATUS current
    DESCRIPTION
	"The access path number for which the access list is related."
    ::= { ipNewCfgAspathEntry 2 }

ipNewCfgAspathAS OBJECT-TYPE
    SYNTAX INTEGER (0..65535)
    MAX-ACCESS read-create
    STATUS current
    DESCRIPTION
	"The AS number of the route map access path.
	 0 means none"
    ::= { ipNewCfgAspathEntry 3 }

ipNewCfgAspathAction OBJECT-TYPE
    SYNTAX INTEGER {
	permit(1),
	deny(2)
	}
    MAX-ACCESS read-create
    STATUS current
    DESCRIPTION
	"Action of the route map access path."
    ::= { ipNewCfgAspathEntry 4 }

ipNewCfgAspathState OBJECT-TYPE
    SYNTAX INTEGER {
        enabled(1),
        disabled(2)
	}
    MAX-ACCESS  read-create
    STATUS  current
    DESCRIPTION
	"Enable or disable the route map access path."
    ::= { ipNewCfgAspathEntry 5 }

ipNewCfgAspathDelete OBJECT-TYPE
    SYNTAX  INTEGER {
	other(1),
	delete(2)
	}
    MAX-ACCESS  read-create
    STATUS  current
    DESCRIPTION
	"When set to the value of 2 (delete), the entire row is deleted.
	 When read, other(1) is returned. Setting the value to anything
	 other than 2(delete) has no effect on the state of the row."
    ::= { ipNewCfgAspathEntry 6 }

--
-- IP BGP configuration
--
bgpGeneral	OBJECT IDENTIFIER ::= { bgpCfg 1 }

bgpCurCfgState OBJECT-TYPE
    SYNTAX INTEGER {
        on(1),
        off(2)
        }
    MAX-ACCESS read-only
    STATUS current
    DESCRIPTION
	"BGP global state."
    ::= { bgpGeneral 1 }

bgpNewCfgState OBJECT-TYPE
    SYNTAX INTEGER {
        on(1),
        off(2)
        }
    MAX-ACCESS read-write
    STATUS current
    DESCRIPTION
	"Globally turn BGP on or off."
    ::= { bgpGeneral 2 }

bgpCurCfgLocalPref OBJECT-TYPE
    SYNTAX Unsigned32 (0..4294967294)
    MAX-ACCESS  read-only
    STATUS  current
    DESCRIPTION
        "Local preference value."
      ::= { bgpGeneral 3 }

bgpNewCfgLocalPref OBJECT-TYPE
    SYNTAX Unsigned32 (0..4294967294)
    MAX-ACCESS  read-write
    STATUS  current
    DESCRIPTION
        "Local Preference value."
      ::= { bgpGeneral 4 }

bgpCurCfgMaxASPath OBJECT-TYPE
    SYNTAX Unsigned32 (1..127)
    MAX-ACCESS  read-only
    STATUS  current
    DESCRIPTION
        "Maximum AS Path Length."
      ::= { bgpGeneral 5 }

bgpNewCfgMaxASPath OBJECT-TYPE
    SYNTAX Unsigned32 (1..127)
    MAX-ACCESS  read-write
    STATUS  current
    DESCRIPTION
        "Maximum AS Path Length."
      ::= { bgpGeneral 6 }

bgpCurCfgASNumber OBJECT-TYPE
    SYNTAX Unsigned32 (0..65535)
    MAX-ACCESS  read-only
    STATUS  current
    DESCRIPTION
        "Current autonomous system number."
      ::= { bgpGeneral 7 }

bgpNewCfgASNumber OBJECT-TYPE
    SYNTAX Unsigned32 (0..65535)
    MAX-ACCESS  read-write
    STATUS  current
    DESCRIPTION
        "New autonomous system number.Enter 0 to delete this number."
      ::= { bgpGeneral 8 }

bgpPeerTableMax OBJECT-TYPE
    SYNTAX Integer32
    MAX-ACCESS read-only
    STATUS current
    DESCRIPTION
	"The maximum number of rows in the BGP peer table."
    ::= { bgpCfg 2 }

bgpCurCfgPeerTable OBJECT-TYPE
    SYNTAX SEQUENCE OF BgpCurCfgPeerEntry
    MAX-ACCESS not-accessible
    STATUS current
    DESCRIPTION
      "The table of BGP peer configuration in the current_config."
    ::= { bgpCfg 3 }

bgpCurCfgPeerEntry OBJECT-TYPE
    SYNTAX BgpCurCfgPeerEntry
    MAX-ACCESS not-accessible
    STATUS current
    DESCRIPTION
      "Information about a BGP peer."
    INDEX { bgpCurCfgPeerIndex }
    ::= { bgpCurCfgPeerTable 1 }

BgpCurCfgPeerEntry ::= SEQUENCE {
    bgpCurCfgPeerIndex     	Integer32,
    bgpCurCfgPeerRemoteAddr	IpAddress,
    bgpCurCfgPeerRemoteAs	INTEGER,
    bgpCurCfgPeerTtl		INTEGER,
    bgpCurCfgPeerState     	INTEGER,
    bgpCurCfgPeerMetric		Unsigned32,
    bgpCurCfgPeerDefaultAction	INTEGER,
    bgpCurCfgPeerOspfState	INTEGER,
    bgpCurCfgPeerFixedState     INTEGER,
    bgpCurCfgPeerStaticState    INTEGER,
    bgpCurCfgPeerVipState       INTEGER,
    bgpCurCfgPeerInRmapList 	OCTET STRING,
    bgpCurCfgPeerOutRmapList	OCTET STRING,
    bgpCurCfgPeerHoldTime       INTEGER,
    bgpCurCfgPeerKeepAlive      INTEGER,
    bgpCurCfgPeerMinTime        INTEGER,
    bgpCurCfgPeerConRetry       INTEGER,
    bgpCurCfgPeerMinAS          INTEGER,
    bgpCurCfgPeerRipState       INTEGER
    }

bgpCurCfgPeerIndex OBJECT-TYPE
    SYNTAX Integer32
    MAX-ACCESS read-only
    STATUS current
    DESCRIPTION
	"The BGP peer number for which the BGP peer table is related."
    ::= { bgpCurCfgPeerEntry 1 }

bgpCurCfgPeerRemoteAddr OBJECT-TYPE
    SYNTAX IpAddress
    MAX-ACCESS read-only
    STATUS current
    DESCRIPTION
	"The remote IP address of the BGP peer."
    ::= { bgpCurCfgPeerEntry 2 }

bgpCurCfgPeerRemoteAs OBJECT-TYPE
    SYNTAX INTEGER (0..65535)
    MAX-ACCESS read-only
    STATUS current
    DESCRIPTION
	"The remote AS number of the BGP peer.  0 means none"
    ::= { bgpCurCfgPeerEntry 3 }

bgpCurCfgPeerTtl OBJECT-TYPE
    SYNTAX INTEGER (1..255)
    MAX-ACCESS read-only
    STATUS current
    DESCRIPTION
	"The time-to-live value of the BGP peer IP datagram. "
    ::= { bgpCurCfgPeerEntry 4 }

bgpCurCfgPeerState OBJECT-TYPE
    SYNTAX INTEGER {
        enabled(1),
        disabled(2)
	}
    MAX-ACCESS  read-only
    STATUS  current
    DESCRIPTION
	"Enable or disable the peer."
    ::= { bgpCurCfgPeerEntry 5 }

bgpCurCfgPeerMetric OBJECT-TYPE
    SYNTAX Unsigned32 (0..4294967294)
    MAX-ACCESS read-only
    STATUS current
    DESCRIPTION
	"The metric value of the BGP peer.  A value of '0' means none"
    ::= { bgpCurCfgPeerEntry 10 }

bgpCurCfgPeerDefaultAction OBJECT-TYPE
    SYNTAX INTEGER {
        none(1),
        import(2),
	originate(3),
	redistribute(4)
	}
    MAX-ACCESS  read-only
    STATUS  current
    DESCRIPTION
	"The value of default route action."
    ::= { bgpCurCfgPeerEntry 11 }

bgpCurCfgPeerOspfState OBJECT-TYPE
    SYNTAX INTEGER {
        enabled(1),
        disabled(2)
	}
    MAX-ACCESS  read-only
    STATUS  current
    DESCRIPTION
	"Enable or disable advertising OSPF routes."
    ::= { bgpCurCfgPeerEntry 12 }

bgpCurCfgPeerFixedState OBJECT-TYPE
    SYNTAX INTEGER {
        enabled(1),
        disabled(2)
	}
    MAX-ACCESS  read-only
    STATUS  current
    DESCRIPTION
	"Enable or disable advertising fixed routes."
    ::= { bgpCurCfgPeerEntry 13 }

bgpCurCfgPeerStaticState OBJECT-TYPE
    SYNTAX INTEGER {
        enabled(1),
        disabled(2)
	}
    MAX-ACCESS  read-only
    STATUS  current
    DESCRIPTION
	"Enable or disable advertising static routes."
    ::= { bgpCurCfgPeerEntry 14 }

bgpCurCfgPeerVipState OBJECT-TYPE
    SYNTAX INTEGER {
        enabled(1),
        disabled(2)
	}
    MAX-ACCESS  read-only
    STATUS  current
    DESCRIPTION
	"Enable or disable VIP static routes."
    ::= { bgpCurCfgPeerEntry 15 }

bgpCurCfgPeerInRmapList OBJECT-TYPE
    SYNTAX OCTET STRING
    MAX-ACCESS read-only
    STATUS current
    DESCRIPTION
        "The route maps present in the in route map list.
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { bgpCurCfgPeerEntry 16 }

bgpCurCfgPeerOutRmapList OBJECT-TYPE
    SYNTAX OCTET STRING
    MAX-ACCESS read-only
    STATUS current
    DESCRIPTION
        "The route maps present in the out route map list.
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { bgpCurCfgPeerEntry 17 }

bgpCurCfgPeerHoldTime OBJECT-TYPE
    SYNTAX INTEGER (1..255)
    MAX-ACCESS read-only
    STATUS current
    DESCRIPTION
        "The Hold Time value of the BGP peer IP datagram. "
    ::= { bgpCurCfgPeerEntry 18 }

bgpCurCfgPeerKeepAlive OBJECT-TYPE
    SYNTAX INTEGER (1..21845)
    MAX-ACCESS read-only
    STATUS current
    DESCRIPTION
        "The KeepAlive Time value of the BGP peer IP datagram. "
    ::= { bgpCurCfgPeerEntry 19 }

bgpCurCfgPeerMinTime OBJECT-TYPE
    SYNTAX INTEGER (1..65535)
    MAX-ACCESS read-only
    STATUS current
    DESCRIPTION
        "The min time between advertisements  of the BGP peer IP datagram. "
    ::= { bgpCurCfgPeerEntry 20 }


bgpCurCfgPeerConRetry OBJECT-TYPE
    SYNTAX INTEGER (1..65535)
    MAX-ACCESS read-only
    STATUS current
    DESCRIPTION
        "The Connect Retry Timer Interval value of the BGP peer IP datagram. "
    ::= { bgpCurCfgPeerEntry 21 }

bgpCurCfgPeerMinAS OBJECT-TYPE
    SYNTAX INTEGER (30..65535)
    MAX-ACCESS read-only
    STATUS current
    DESCRIPTION
        "The minimum time between route originations of the BGP peer IP datagram."
    ::= { bgpCurCfgPeerEntry 22 }

bgpCurCfgPeerRipState OBJECT-TYPE
    SYNTAX INTEGER {
        enabled(1),
        disabled(2)
        }
    MAX-ACCESS  read-only
    STATUS  current
    DESCRIPTION
        "Enable or disable RIP static routes."
    ::= { bgpCurCfgPeerEntry 23 }

bgpNewCfgPeerTable OBJECT-TYPE
    SYNTAX SEQUENCE OF BgpNewCfgPeerEntry
    MAX-ACCESS not-accessible
    STATUS current
    DESCRIPTION
      "The table of BGP peer configuration in the current_config."
    ::= { bgpCfg 4 }

bgpNewCfgPeerEntry OBJECT-TYPE
    SYNTAX BgpNewCfgPeerEntry
    MAX-ACCESS not-accessible
    STATUS current
    DESCRIPTION
      "Information about a BGP peer."
    INDEX { bgpNewCfgPeerIndex }
    ::= { bgpNewCfgPeerTable 1 }

BgpNewCfgPeerEntry ::= SEQUENCE {
    bgpNewCfgPeerIndex     	Integer32,
    bgpNewCfgPeerRemoteAddr	IpAddress,
    bgpNewCfgPeerRemoteAs	INTEGER,
    bgpNewCfgPeerTtl		INTEGER,
    bgpNewCfgPeerState     	INTEGER,
    bgpNewCfgPeerDelete		INTEGER,
    bgpNewCfgPeerMetric		Unsigned32,
    bgpNewCfgPeerDefaultAction	INTEGER,
    bgpNewCfgPeerOspfState	INTEGER,
    bgpNewCfgPeerFixedState     INTEGER,
    bgpNewCfgPeerStaticState    INTEGER,
    bgpNewCfgPeerVipState       INTEGER,
    bgpNewCfgPeerInRmapList	OCTET STRING,
    bgpNewCfgPeerOutRmapList	OCTET STRING,
    bgpNewCfgPeerAddInRmap	Integer32,
    bgpNewCfgPeerAddOutRmap	Integer32,
    bgpNewCfgPeerRemoveInRmap	Integer32,
    bgpNewCfgPeerRemoveOutRmap	Integer32,
    bgpNewCfgPeerHoldTime       INTEGER,
    bgpNewCfgPeerKeepAlive      INTEGER,
    bgpNewCfgPeerMinTime        INTEGER,
    bgpNewCfgPeerConRetry       INTEGER,
    bgpNewCfgPeerMinAS          INTEGER,
    bgpNewCfgPeerRipState       INTEGER
    }

bgpNewCfgPeerIndex OBJECT-TYPE
    SYNTAX Integer32
    MAX-ACCESS read-only
    STATUS current
    DESCRIPTION
	"The BGP peer number for which the BGP peer table is related."
    ::= { bgpNewCfgPeerEntry 1}

bgpNewCfgPeerRemoteAddr OBJECT-TYPE
    SYNTAX IpAddress
    MAX-ACCESS read-create
    STATUS current
    DESCRIPTION
	"The remote IP address of the BGP peer."
    ::= { bgpNewCfgPeerEntry 2 }

bgpNewCfgPeerRemoteAs OBJECT-TYPE
    SYNTAX INTEGER (0..65535)
    MAX-ACCESS read-create
    STATUS current
    DESCRIPTION
	"The remote AS number of the BGP peer.  0 means none"
    ::= { bgpNewCfgPeerEntry 3 }

bgpNewCfgPeerTtl OBJECT-TYPE
    SYNTAX INTEGER (1..255)
    MAX-ACCESS read-create
    STATUS current
    DESCRIPTION
	"The time-to-live value of the BGP peer IP datagram. "
    ::= { bgpNewCfgPeerEntry 4 }

bgpNewCfgPeerState OBJECT-TYPE
    SYNTAX INTEGER {
        enabled(1),
        disabled(2)
	}
    MAX-ACCESS  read-create
    STATUS  current
    DESCRIPTION
	"Enable or disable the peer."
    ::= { bgpNewCfgPeerEntry 5 }

bgpNewCfgPeerDelete OBJECT-TYPE
    SYNTAX INTEGER {
        other(1),
        delete(2)
        }
    MAX-ACCESS read-create
    STATUS current
    DESCRIPTION
	"When set to the value of 2 (delete), the entire row is deleted.
	 When read, other(1) is returned. Setting the value to anything
	 other than 2(delete) has no effect on the state of the row."
    ::= { bgpNewCfgPeerEntry 6 }

bgpNewCfgPeerMetric OBJECT-TYPE
    SYNTAX Unsigned32 (0..4294967294)
    MAX-ACCESS read-create
    STATUS current
    DESCRIPTION
	"The metric value of the BGP peer. A value of '0' means none"
    ::= { bgpNewCfgPeerEntry 10 }

bgpNewCfgPeerDefaultAction OBJECT-TYPE
    SYNTAX INTEGER {
        none(1),
        import(2),
	originate(3),
	redistribute(4)
	}
    MAX-ACCESS  read-create
    STATUS  current
    DESCRIPTION
	"The value of default route action."
    ::= { bgpNewCfgPeerEntry 11 }

bgpNewCfgPeerOspfState OBJECT-TYPE
    SYNTAX INTEGER {
        enabled(1),
        disabled(2)
	}
    MAX-ACCESS  read-create
    STATUS  current
    DESCRIPTION
	"Enable or disable advertising OSPF routes."
    ::= { bgpNewCfgPeerEntry 12 }

bgpNewCfgPeerFixedState OBJECT-TYPE
    SYNTAX INTEGER {
        enabled(1),
        disabled(2)
	}
    MAX-ACCESS  read-create
    STATUS  current
    DESCRIPTION
	"Enable or disable advertising fixed routes."
    ::= { bgpNewCfgPeerEntry 13 }

bgpNewCfgPeerStaticState OBJECT-TYPE
    SYNTAX INTEGER {
        enabled(1),
        disabled(2)
	}
    MAX-ACCESS  read-create
    STATUS  current
    DESCRIPTION
	"Enable or disable advertising static routes."
    ::= { bgpNewCfgPeerEntry 14 }

bgpNewCfgPeerVipState OBJECT-TYPE
    SYNTAX INTEGER {
        enabled(1),
        disabled(2)
	}
    MAX-ACCESS  read-create
    STATUS  current
    DESCRIPTION
	"Enable or disable VIP static routes."
    ::= { bgpNewCfgPeerEntry 15 }

bgpNewCfgPeerInRmapList OBJECT-TYPE
    SYNTAX OCTET STRING
    MAX-ACCESS read-only
    STATUS current
    DESCRIPTION
        "The route maps present in the in route map list.
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { bgpNewCfgPeerEntry 16 }

bgpNewCfgPeerOutRmapList OBJECT-TYPE
    SYNTAX OCTET STRING
    MAX-ACCESS read-only
    STATUS current
    DESCRIPTION
        "The route maps present in the out route map list.
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { bgpNewCfgPeerEntry 17 }

bgpNewCfgPeerAddInRmap OBJECT-TYPE
    SYNTAX Integer32
    MAX-ACCESS  read-create
    STATUS  current
    DESCRIPTION
	"The route map to be add into in-rmap list. When read,
	 0 is returned."
    ::= { bgpNewCfgPeerEntry 18 }

bgpNewCfgPeerAddOutRmap OBJECT-TYPE
    SYNTAX Integer32
    MAX-ACCESS  read-create
    STATUS  current
    DESCRIPTION
	"The route map to be add into out-rmap list. When read,
	 0 is returned."
    ::= { bgpNewCfgPeerEntry 19 }

bgpNewCfgPeerRemoveInRmap OBJECT-TYPE
    SYNTAX Integer32
    MAX-ACCESS  read-create
    STATUS  current
    DESCRIPTION
	"The route map to be removed from out-rmap list. When read,
	 0 is returned."
    ::= { bgpNewCfgPeerEntry 20 }

bgpNewCfgPeerRemoveOutRmap OBJECT-TYPE
    SYNTAX Integer32
    MAX-ACCESS  read-create
    STATUS  current
    DESCRIPTION
	"The route map to be removed from out-rmap list. When read,
	 0 is returned."
    ::= { bgpNewCfgPeerEntry 21 }

bgpNewCfgPeerHoldTime OBJECT-TYPE
    SYNTAX INTEGER (0..65535)
    MAX-ACCESS read-create
    STATUS current
    DESCRIPTION
        "The Hold Time value of the BGP peer IP datagram. "
    ::= { bgpNewCfgPeerEntry 22 }

bgpNewCfgPeerKeepAlive OBJECT-TYPE
    SYNTAX INTEGER (1..21845)
    MAX-ACCESS read-create
    STATUS current
    DESCRIPTION
        "The KeepAlive Time value of the BGP peer IP datagram. "
    ::= { bgpNewCfgPeerEntry 23 }

bgpNewCfgPeerMinTime OBJECT-TYPE
    SYNTAX INTEGER (1..65535)
    MAX-ACCESS read-create
    STATUS current
    DESCRIPTION
        "The mininum time between advertisements of the BGP peer IP datagram. "
    ::= { bgpNewCfgPeerEntry 24 }


bgpNewCfgPeerConRetry OBJECT-TYPE
    SYNTAX INTEGER (1..65535)
    MAX-ACCESS read-create
    STATUS current
    DESCRIPTION
        "The Connect Retry Timer Interval value of the BGP peer IP datagram. "
    ::= { bgpNewCfgPeerEntry 25 }

bgpNewCfgPeerMinAS OBJECT-TYPE
    SYNTAX INTEGER (30..65535)
    MAX-ACCESS read-create
    STATUS current
    DESCRIPTION
        "The minimum time between route originations of the BGP peer IP datagram. "
    ::= { bgpNewCfgPeerEntry 26 }

bgpNewCfgPeerRipState OBJECT-TYPE
    SYNTAX INTEGER {
        enabled(1),
        disabled(2)
        }
    MAX-ACCESS  read-create
    STATUS  current
    DESCRIPTION
        "Enable or disable RIP static routes."
    ::= { bgpNewCfgPeerEntry 27 }

--
-- BGP Aggregation Table
--
bgpAggrTableMax OBJECT-TYPE
    SYNTAX Integer32
    MAX-ACCESS read-only
    STATUS current
    DESCRIPTION
	"The maximum number of rows in the BGP aggregation table."
    ::= { bgpCfg 5 }

bgpCurCfgAggrTable OBJECT-TYPE
    SYNTAX SEQUENCE OF BgpCurCfgAggrEntry
    MAX-ACCESS not-accessible
    STATUS current
    DESCRIPTION
      "The table of BGP aggregation configuration."
    ::= { bgpCfg 6 }

bgpCurCfgAggrEntry OBJECT-TYPE
    SYNTAX BgpCurCfgAggrEntry
    MAX-ACCESS not-accessible
    STATUS current
    DESCRIPTION
      "Information about a BGP aggregation."
    INDEX { bgpCurCfgAggrIndex }
    ::= { bgpCurCfgAggrTable 1 }

BgpCurCfgAggrEntry ::= SEQUENCE {
    bgpCurCfgAggrIndex     Integer32,
    bgpCurCfgAggrAddr      IpAddress,
    bgpCurCfgAggrMask      IpAddress,
    bgpCurCfgAggrState     INTEGER
    }

bgpCurCfgAggrIndex OBJECT-TYPE
    SYNTAX Integer32
    MAX-ACCESS read-only
    STATUS current
    DESCRIPTION
	"The aggregation number for which the BGP aggregation is related."
    ::= { bgpCurCfgAggrEntry 1}

bgpCurCfgAggrAddr OBJECT-TYPE
    SYNTAX IpAddress
    MAX-ACCESS read-only
    STATUS current
    DESCRIPTION
	"The IP address of the BGP aggregation."
    ::= { bgpCurCfgAggrEntry 2 }

bgpCurCfgAggrMask OBJECT-TYPE
    SYNTAX IpAddress
    MAX-ACCESS read-only
    STATUS current
    DESCRIPTION
	"The subnet mask of the BGP aggregation."
    ::= { bgpCurCfgAggrEntry 3 }

bgpCurCfgAggrState OBJECT-TYPE
    SYNTAX INTEGER {
        enabled(1),
        disabled(2)
	}
    MAX-ACCESS  read-only
    STATUS  current
    DESCRIPTION
	"Enable or disable the BGP aggregation."
    ::= { bgpCurCfgAggrEntry 4 }

bgpNewCfgAggrTable OBJECT-TYPE
    SYNTAX SEQUENCE OF BgpNewCfgAggrEntry
    MAX-ACCESS not-accessible
    STATUS current
    DESCRIPTION
      "The table of BGP aggregation configuration."
    ::= { bgpCfg 7 }

bgpNewCfgAggrEntry OBJECT-TYPE
    SYNTAX BgpNewCfgAggrEntry
    MAX-ACCESS not-accessible
    STATUS current
    DESCRIPTION
      "Information about an BGP aggregation."
    INDEX { bgpNewCfgAggrIndex }
    ::= { bgpNewCfgAggrTable 1 }

BgpNewCfgAggrEntry ::= SEQUENCE {
    bgpNewCfgAggrIndex     Integer32,
    bgpNewCfgAggrAddr      IpAddress,
    bgpNewCfgAggrMask      IpAddress,
    bgpNewCfgAggrState     INTEGER,
    bgpNewCfgAggrDelete    INTEGER
    }

bgpNewCfgAggrIndex OBJECT-TYPE
    SYNTAX Integer32
    MAX-ACCESS read-only
    STATUS current
    DESCRIPTION
	"The aggregation number for which the BGP aggregation is related."
    ::= { bgpNewCfgAggrEntry 1}

bgpNewCfgAggrAddr OBJECT-TYPE
    SYNTAX IpAddress
    MAX-ACCESS read-create
    STATUS current
    DESCRIPTION
	"The IP address of the BGP aggregation."
    ::= { bgpNewCfgAggrEntry 2 }

bgpNewCfgAggrMask OBJECT-TYPE
    SYNTAX IpAddress
    MAX-ACCESS read-create
    STATUS current
    DESCRIPTION
	"The subnet mask of the BGP aggregation."
    ::= { bgpNewCfgAggrEntry 3 }

bgpNewCfgAggrState OBJECT-TYPE
    SYNTAX INTEGER {
        enabled(1),
        disabled(2)
	}
    MAX-ACCESS  read-create
    STATUS  current
    DESCRIPTION
	"Enable or disable the BGP aggregation."
    ::= { bgpNewCfgAggrEntry 4 }

bgpNewCfgAggrDelete OBJECT-TYPE
    SYNTAX INTEGER {
        other(1),
        delete(2)
        }
    MAX-ACCESS read-create
    STATUS current
    DESCRIPTION
	"When set to the value of 2 (delete), the entire row is deleted.
	 When read, other(1) is returned. Setting the value to anything
	 other than 2(delete) has no effect on the state of the row."
    ::= { bgpNewCfgAggrEntry 5 }

--
-- IP OSPF configuration
--
ospfGeneral	OBJECT IDENTIFIER ::= { ospfCfg 1 }

ospfCurCfgDefaultRouteMetric OBJECT-TYPE
    SYNTAX INTEGER (0..16777215)
    MAX-ACCESS read-only
    STATUS current
    DESCRIPTION
	"Specify the metric to be assigned."
    ::= { ospfGeneral 1 }

ospfNewCfgDefaultRouteMetric OBJECT-TYPE
    SYNTAX INTEGER (0..16777215)
    MAX-ACCESS read-write
    STATUS current
    DESCRIPTION
	"Specify the metric to be assigned."
    ::= { ospfGeneral 2 }

ospfCurCfgDefaultRouteMetricType OBJECT-TYPE
    SYNTAX INTEGER {
        none(1),
        type1(2),
        type2(3)
        }
    MAX-ACCESS read-only
    STATUS current
    DESCRIPTION
	"Specify the AS External metric type to be assigned."
    ::= { ospfGeneral 3 }

ospfNewCfgDefaultRouteMetricType OBJECT-TYPE
    SYNTAX INTEGER {
        none(1),
        type1(2),
        type2(3)
        }
    MAX-ACCESS read-write
    STATUS current
    DESCRIPTION
	"Specify the AS External metric type to be assigned."
    ::= { ospfGeneral 4 }

ospfIntfTableMaxSize OBJECT-TYPE
    SYNTAX Integer32
    MAX-ACCESS read-only
    STATUS current
    DESCRIPTION
        "The maximum number of rows in the OSPF Interface table."
    ::= { ospfGeneral 5 }

ospfAreaTableMaxSize OBJECT-TYPE
    SYNTAX Integer32
    MAX-ACCESS read-only
    STATUS current
    DESCRIPTION
        "The maximum number of rows in the OSPF Area table."
    ::= { ospfGeneral 6 }

ospfRangeTableMaxSize OBJECT-TYPE
    SYNTAX Integer32
    MAX-ACCESS read-only
    STATUS current
    DESCRIPTION
        "The maximum number of rows in the OSPF Range table."
    ::= { ospfGeneral 7 }

ospfVirtIntfTableMaxSize OBJECT-TYPE
    SYNTAX Integer32
    MAX-ACCESS read-only
    STATUS current
    DESCRIPTION
        "The maximum number of rows in the OSPF Virtual Interface
         table."
    ::= { ospfGeneral 8 }

ospfHostTableMaxSize OBJECT-TYPE
    SYNTAX Integer32
    MAX-ACCESS read-only
    STATUS current
    DESCRIPTION
        "The maximum number of rows in the OSPF Host table."
    ::= { ospfGeneral 9 }

ospfCurCfgState OBJECT-TYPE
    SYNTAX INTEGER {
        on(1),
        off(2)
        }
    MAX-ACCESS read-only
    STATUS current
    DESCRIPTION
	"OSPF global state."
    ::= { ospfGeneral 10 }

ospfNewCfgState OBJECT-TYPE
    SYNTAX INTEGER {
        on(1),
        off(2)
        }
    MAX-ACCESS read-write
    STATUS current
    DESCRIPTION
	"Globally turn OSPF on or off."
    ::= { ospfGeneral 11 }

ospfCurCfgLsdb OBJECT-TYPE
    SYNTAX INTEGER (0..2000)
    MAX-ACCESS read-only
    STATUS current
    DESCRIPTION
        "Specify the LSDB limit for external LSA."
    ::= { ospfGeneral 12 }

ospfNewCfgLsdb OBJECT-TYPE
    SYNTAX INTEGER (0..2000)
    MAX-ACCESS read-write
    STATUS current
    DESCRIPTION
        "Specify the LSDB limit for external LSA."
    ::= { ospfGeneral 13 }

ospfCurCfgAreaTable OBJECT-TYPE
    SYNTAX SEQUENCE OF OspfCurCfgAreaEntry
    MAX-ACCESS not-accessible
    STATUS current
    DESCRIPTION
      "The table of OSPF Area configuration in the current_config."
    ::= { ospfCfg 2 }

ospfCurCfgAreaEntry OBJECT-TYPE
    SYNTAX OspfCurCfgAreaEntry
    MAX-ACCESS not-accessible
    STATUS current
    DESCRIPTION
      "Information about a OSPF area."
    INDEX { ospfCurCfgAreaIndex, ospfCurCfgAreaId }
    ::= { ospfCurCfgAreaTable 1 }

OspfCurCfgAreaEntry ::= SEQUENCE {
    ospfCurCfgAreaIndex         Integer32,
    ospfCurCfgAreaId            IpAddress,
    ospfCurCfgAreaSpfInterval   INTEGER,
    ospfCurCfgAreaAuthType      INTEGER,
    ospfCurCfgAreaType          INTEGER,
    ospfCurCfgAreaMetric        INTEGER,
    ospfCurCfgAreaState         INTEGER
    }

ospfCurCfgAreaIndex OBJECT-TYPE
    SYNTAX Integer32
    MAX-ACCESS read-only
    STATUS current
    DESCRIPTION
	"The OSPF area number for which the OSPF area table is related."
    ::= { ospfCurCfgAreaEntry 1}

ospfCurCfgAreaId OBJECT-TYPE
    SYNTAX IpAddress
    MAX-ACCESS read-only
    STATUS current
    DESCRIPTION
	"The IP Address of the OSPF area."
    ::= { ospfCurCfgAreaEntry 2 }

ospfCurCfgAreaSpfInterval OBJECT-TYPE
    SYNTAX INTEGER (0..255)
    MAX-ACCESS read-only
    STATUS current
    DESCRIPTION
	"The SPF interval for the OSPF area."
    ::= { ospfCurCfgAreaEntry 3 }

ospfCurCfgAreaAuthType OBJECT-TYPE
    SYNTAX  INTEGER {
        none(1),
        password(2),
	md5(3)
        }
    MAX-ACCESS  read-only
    STATUS  current
    DESCRIPTION
        "Type of authentication being used.
	 none(1) - no authentication
	 password(2) - use password
	 md5(3) - use MD5 authentication."

    ::= { ospfCurCfgAreaEntry 4 }

ospfCurCfgAreaType OBJECT-TYPE
    SYNTAX  INTEGER {
        transit(1),
        stub(2),
        nssa(3)
        }
    MAX-ACCESS  read-only
    STATUS  current
    DESCRIPTION
        "Type of area being used."
    ::= { ospfCurCfgAreaEntry 5 }

ospfCurCfgAreaMetric OBJECT-TYPE
    SYNTAX INTEGER (1..65535)
    MAX-ACCESS read-only
    STATUS current
    DESCRIPTION
        "The Stub area metric for the OSPF area."
    ::= { ospfCurCfgAreaEntry 6 }

ospfCurCfgAreaState OBJECT-TYPE
    SYNTAX INTEGER {
        on(1),
        off(2)
        }
    MAX-ACCESS read-only
    STATUS current
    DESCRIPTION
        "Globally turn OSPF on or off."
    ::= { ospfCurCfgAreaEntry 7 }

ospfNewCfgAreaTable OBJECT-TYPE
    SYNTAX SEQUENCE OF OspfNewCfgAreaEntry
    MAX-ACCESS not-accessible
    STATUS current
    DESCRIPTION
      "The table of OSPF Area configuration in the new_config."
    ::= { ospfCfg 3 }

ospfNewCfgAreaEntry OBJECT-TYPE
    SYNTAX OspfNewCfgAreaEntry
    MAX-ACCESS not-accessible
    STATUS current
    DESCRIPTION
      "Information about a OSPF area."
    INDEX { ospfNewCfgAreaIndex, ospfNewCfgAreaId }
    ::= { ospfNewCfgAreaTable 1 }

OspfNewCfgAreaEntry ::= SEQUENCE {
    ospfNewCfgAreaIndex         Integer32,
    ospfNewCfgAreaId            IpAddress,
    ospfNewCfgAreaSpfInterval   INTEGER,
    ospfNewCfgAreaAuthType      INTEGER,
    ospfNewCfgAreaType          INTEGER,
    ospfNewCfgAreaMetric        INTEGER,
    ospfNewCfgAreaState         INTEGER,
    ospfNewCfgAreaDelete        INTEGER
    }

ospfNewCfgAreaIndex OBJECT-TYPE
    SYNTAX Integer32
    MAX-ACCESS read-only
    STATUS current
    DESCRIPTION
	"The OSPF area number for which the OSPF area table is related."
    ::= { ospfNewCfgAreaEntry 1}

ospfNewCfgAreaId OBJECT-TYPE
    SYNTAX IpAddress
    MAX-ACCESS read-only
    STATUS current
    DESCRIPTION
	"The IP Address of the OSPF area."
    ::= { ospfNewCfgAreaEntry 2 }

ospfNewCfgAreaSpfInterval OBJECT-TYPE
    SYNTAX INTEGER (0..255)
    MAX-ACCESS read-create
    STATUS current
    DESCRIPTION
	"The SPF interval for the OSPF area."
    ::= { ospfNewCfgAreaEntry 3 }

ospfNewCfgAreaAuthType OBJECT-TYPE
    SYNTAX  INTEGER {
        none(1),
        password(2),
	md5(3)
        }
    MAX-ACCESS  read-create
    STATUS  current
    DESCRIPTION
        "Type of authentication being used.
	 none(1) - no authentication
	 password(2) - use password.
         md5(3) - use MD5 authentication."
    ::= { ospfNewCfgAreaEntry 4 }

ospfNewCfgAreaType OBJECT-TYPE
    SYNTAX  INTEGER {
        transit(1),
        stub(2),
        nssa(3)
        }
    MAX-ACCESS  read-create
    STATUS  current
    DESCRIPTION
        "Type of area being used."
    ::= { ospfNewCfgAreaEntry 5 }

ospfNewCfgAreaMetric OBJECT-TYPE
    SYNTAX INTEGER (1..65535)
    MAX-ACCESS read-create
    STATUS current
    DESCRIPTION
        "The Stub area metric for the OSPF area."
    ::= { ospfNewCfgAreaEntry 6 }

ospfNewCfgAreaState OBJECT-TYPE
    SYNTAX INTEGER {
        enabled(1),
        disabled(2)
        }
    MAX-ACCESS read-create
    STATUS current
    DESCRIPTION
        "Enable or disable OSPF Area."
    ::= { ospfNewCfgAreaEntry 7 }

ospfNewCfgAreaDelete OBJECT-TYPE
    SYNTAX INTEGER {
        other(1),
        delete(2)
        }
    MAX-ACCESS read-create
    STATUS current
    DESCRIPTION
        "When set to the value of 2 (delete), the entire row is deleted.
         When read, other(1) is returned. Setting the value to anything
         other than 2(delete) has no effect on the state of the row."
    ::= { ospfNewCfgAreaEntry 8 }



ospfNewCfgVisionAreaTable OBJECT-TYPE
    SYNTAX SEQUENCE OF OspfNewCfgVisionAreaEntry
    MAX-ACCESS not-accessible
    STATUS current
    DESCRIPTION
      "The table of OSPF Area configuration in the new_config."
    ::= { ospfCfg 16 }

ospfNewCfgVisionAreaEntry OBJECT-TYPE
    SYNTAX OspfNewCfgVisionAreaEntry
    MAX-ACCESS not-accessible
    STATUS current
    DESCRIPTION
      "Information about a OSPF area."
    INDEX { ospfNewCfgVisionAreaIndex }
    ::= { ospfNewCfgVisionAreaTable 1 }

OspfNewCfgVisionAreaEntry ::= SEQUENCE {
    ospfNewCfgVisionAreaIndex         Integer32,
    ospfNewCfgVisionAreaId            IpAddress,
    ospfNewCfgVisionAreaSpfInterval   INTEGER,
    ospfNewCfgVisionAreaAuthType      INTEGER,
    ospfNewCfgVisionAreaType          INTEGER,
    ospfNewCfgVisionAreaMetric        INTEGER,
    ospfNewCfgVisionAreaState         INTEGER,
    ospfNewCfgVisionAreaDelete        INTEGER
    }

ospfNewCfgVisionAreaIndex OBJECT-TYPE
    SYNTAX Integer32
    MAX-ACCESS read-only
    STATUS current
    DESCRIPTION
    "The OSPF area number for which the OSPF area table is related."
    ::= { ospfNewCfgVisionAreaEntry 1}

ospfNewCfgVisionAreaId OBJECT-TYPE
    SYNTAX IpAddress
    MAX-ACCESS read-write
    STATUS current
    DESCRIPTION
    "The IP Address of the OSPF area."
    ::= { ospfNewCfgVisionAreaEntry 2 }

ospfNewCfgVisionAreaSpfInterval OBJECT-TYPE
    SYNTAX INTEGER (0..255)
    MAX-ACCESS read-create
    STATUS current
    DESCRIPTION
    "The SPF interval for the OSPF area."
    ::= { ospfNewCfgVisionAreaEntry 3 }

ospfNewCfgVisionAreaAuthType OBJECT-TYPE
    SYNTAX  INTEGER {
        none(1),
        password(2),
    md5(3)
        }
    MAX-ACCESS  read-create
    STATUS  current
    DESCRIPTION
        "Type of authentication being used.
     none(1) - no authentication
     password(2) - use password.
         md5(3) - use MD5 authentication."
    ::= { ospfNewCfgVisionAreaEntry 4 }

ospfNewCfgVisionAreaType OBJECT-TYPE
    SYNTAX  INTEGER {
        transit(1),
        stub(2),
        nssa(3)
        }
    MAX-ACCESS  read-create
    STATUS  current
    DESCRIPTION
        "Type of area being used."
    ::= { ospfNewCfgVisionAreaEntry 5 }

ospfNewCfgVisionAreaMetric OBJECT-TYPE
    SYNTAX INTEGER (1..65535)
    MAX-ACCESS read-create
    STATUS current
    DESCRIPTION
        "The Stub area metric for the OSPF area."
    ::= { ospfNewCfgVisionAreaEntry 6 }

ospfNewCfgVisionAreaState OBJECT-TYPE
    SYNTAX INTEGER {
        enabled(1),
        disabled(2)
        }
    MAX-ACCESS read-create
    STATUS current
    DESCRIPTION
        "Enable or disable OSPF Area."
    ::= { ospfNewCfgVisionAreaEntry 7 }

ospfNewCfgVisionAreaDelete OBJECT-TYPE
    SYNTAX INTEGER {
        other(1),
        delete(2)
        }
    MAX-ACCESS read-create
    STATUS current
    DESCRIPTION
        "When set to the value of 2 (delete), the entire row is deleted.
         When read, other(1) is returned. Setting the value to anything
         other than 2(delete) has no effect on the state of the row."
    ::= { ospfNewCfgVisionAreaEntry 8 }


-- OSPF Host Table

ospfCurCfgHostTable OBJECT-TYPE
    SYNTAX SEQUENCE OF OspfCurCfgHostEntry
    MAX-ACCESS not-accessible
    STATUS current
    DESCRIPTION
      "The table of OSPF Host configuration."
    ::= { ospfCfg 12 }

ospfCurCfgHostEntry OBJECT-TYPE
    SYNTAX OspfCurCfgHostEntry
    MAX-ACCESS not-accessible
    STATUS current
    DESCRIPTION
      "Information about a OSPF host."
    INDEX { ospfCurCfgHostIndex }
    ::= { ospfCurCfgHostTable 1 }

OspfCurCfgHostEntry ::= SEQUENCE {
    ospfCurCfgHostIndex         Integer32,
    ospfCurCfgHostIpAddr        IpAddress,
    ospfCurCfgHostAreaIndex     Integer32,
    ospfCurCfgHostCost		INTEGER,
    ospfCurCfgHostState		INTEGER
    }

ospfCurCfgHostIndex OBJECT-TYPE
    SYNTAX Integer32
    MAX-ACCESS read-only
    STATUS current
    DESCRIPTION
	"The OSPF host number for which the OSPF host table is related."
    ::= { ospfCurCfgHostEntry 1}

ospfCurCfgHostIpAddr OBJECT-TYPE
    SYNTAX IpAddress
    MAX-ACCESS read-only
    STATUS current
    DESCRIPTION
	"The IP Address of the OSPF host."
    ::= { ospfCurCfgHostEntry 2 }

ospfCurCfgHostAreaIndex OBJECT-TYPE
    SYNTAX Integer32
    MAX-ACCESS read-only
    STATUS current
    DESCRIPTION
	"The area index."
    ::= { ospfCurCfgHostEntry 3 }

ospfCurCfgHostCost OBJECT-TYPE
    SYNTAX INTEGER (1..65535)
    MAX-ACCESS read-only
    STATUS current
    DESCRIPTION
        "Cost of the host entry."
    ::= { ospfCurCfgHostEntry 4 }

ospfCurCfgHostState OBJECT-TYPE
    SYNTAX INTEGER {
        enabled(1),
        disabled(2)
        }
    MAX-ACCESS read-only
    STATUS current
    DESCRIPTION
        "Enable or disable Host Entry."
    ::= { ospfCurCfgHostEntry 5 }

ospfNewCfgHostTable OBJECT-TYPE
    SYNTAX SEQUENCE OF OspfNewCfgHostEntry
    MAX-ACCESS not-accessible
    STATUS current
    DESCRIPTION
      "The table of OSPF Host configuration."
    ::= { ospfCfg 13 }

ospfNewCfgHostEntry OBJECT-TYPE
    SYNTAX OspfNewCfgHostEntry
    MAX-ACCESS not-accessible
    STATUS current
    DESCRIPTION
      "Information about a OSPF host."
    INDEX { ospfNewCfgHostIndex }
    ::= { ospfNewCfgHostTable 1 }

OspfNewCfgHostEntry ::= SEQUENCE {
    ospfNewCfgHostIndex         Integer32,
    ospfNewCfgHostIpAddr        IpAddress,
    ospfNewCfgHostAreaIndex     Integer32,
    ospfNewCfgHostCost          INTEGER,
    ospfNewCfgHostState         INTEGER,
    ospfNewCfgHostDelete        INTEGER
    }

ospfNewCfgHostIndex OBJECT-TYPE
    SYNTAX Integer32
    MAX-ACCESS read-only
    STATUS current
    DESCRIPTION
	"The OSPF host number for which the OSPF host table is related."
    ::= { ospfNewCfgHostEntry 1}

ospfNewCfgHostIpAddr OBJECT-TYPE
    SYNTAX IpAddress
    MAX-ACCESS read-create
    STATUS current
    DESCRIPTION
	"The IP Address of the OSPF host."
    ::= { ospfNewCfgHostEntry 2 }

ospfNewCfgHostAreaIndex OBJECT-TYPE
    SYNTAX Integer32
    MAX-ACCESS read-create
    STATUS current
    DESCRIPTION
	"The OSPF area index."
    ::= { ospfNewCfgHostEntry 3 }

ospfNewCfgHostCost OBJECT-TYPE
    SYNTAX INTEGER (1..65535)
    MAX-ACCESS read-create
    STATUS current
    DESCRIPTION
        "Cost of the host entry."
    ::= { ospfNewCfgHostEntry 4 }

ospfNewCfgHostState OBJECT-TYPE
    SYNTAX INTEGER {
        enabled(1),
        disabled(2)
        }
    MAX-ACCESS read-create
    STATUS current
    DESCRIPTION
        "Enable or disable Host Entry."
    ::= { ospfNewCfgHostEntry 5 }

ospfNewCfgHostDelete OBJECT-TYPE
    SYNTAX INTEGER {
        other(1),
        delete(2)
        }
    MAX-ACCESS read-create
    STATUS current
    DESCRIPTION
        "When set to the value of 2 (delete), the entire row is deleted.
         When read, other(1) is returned. Setting the value to anything
         other than 2(delete) has no effect on the state of the row."
    ::= { ospfNewCfgHostEntry 6 }

ospfMdkeyTableMaxSize OBJECT-TYPE
    SYNTAX  Integer32
    MAX-ACCESS  read-only
    STATUS  current
    DESCRIPTION
        "The maximum number of rows in the OSPF Mdkey table."
    ::= { ospfCfg 11 }

ospfCurCfgMdkeyTable OBJECT-TYPE
    SYNTAX SEQUENCE OF OspfCurCfgMdkeyEntry
    MAX-ACCESS not-accessible
    STATUS current
    DESCRIPTION
      "The table of OSPF MD5 keys in the current_config."
    ::= { ospfCfg 5 }

ospfCurCfgMdkeyEntry OBJECT-TYPE
    SYNTAX OspfCurCfgMdkeyEntry
    MAX-ACCESS not-accessible
    STATUS current
    DESCRIPTION
      "Information about an OSPF MD keys table."
    INDEX { ospfCurCfgMdkeyIndex }
    ::= { ospfCurCfgMdkeyTable 1 }

OspfCurCfgMdkeyEntry ::= SEQUENCE {
    ospfCurCfgMdkeyIndex        Integer32,
    ospfCurCfgMdkeyKey          DisplayString
    }

ospfCurCfgMdkeyIndex OBJECT-TYPE
    SYNTAX Integer32
    MAX-ACCESS read-only
    STATUS current
    DESCRIPTION
	"The OSPF MD5 Key number for which the OSPF MdKey table is related."
    ::= { ospfCurCfgMdkeyEntry 1}

ospfCurCfgMdkeyKey OBJECT-TYPE
    SYNTAX DisplayString (SIZE(0..16))
    MAX-ACCESS read-only
    STATUS current
    DESCRIPTION
	"The character string representing the MD5 Key."
    ::= { ospfCurCfgMdkeyEntry 2 }

ospfNewCfgMdkeyTable OBJECT-TYPE
    SYNTAX SEQUENCE OF OspfNewCfgMdkeyEntry
    MAX-ACCESS not-accessible
    STATUS current
    DESCRIPTION
      "The table of OSPF MD5 keys in the new_config."
    ::= { ospfCfg 6 }

ospfNewCfgMdkeyEntry OBJECT-TYPE
    SYNTAX OspfNewCfgMdkeyEntry
    MAX-ACCESS not-accessible
    STATUS current
    DESCRIPTION
      "Information about an OSPF MD keys table."
    INDEX { ospfNewCfgMdkeyIndex }
    ::= { ospfNewCfgMdkeyTable 1 }

OspfNewCfgMdkeyEntry ::= SEQUENCE {
    ospfNewCfgMdkeyIndex        Integer32,
    ospfNewCfgMdkeyKey          DisplayString,
    ospfNewCfgMdkeyDelete       INTEGER
    }

ospfNewCfgMdkeyIndex OBJECT-TYPE
    SYNTAX Integer32
    MAX-ACCESS read-only
    STATUS current
    DESCRIPTION
	"The OSPF MD5 Key number for which the OSPF MdKey table is related."
    ::= { ospfNewCfgMdkeyEntry 1}

ospfNewCfgMdkeyKey OBJECT-TYPE
    SYNTAX DisplayString (SIZE(0..16))
    MAX-ACCESS read-create
    STATUS current
    DESCRIPTION
	"The character string representing the MD5 Key."
    ::= { ospfNewCfgMdkeyEntry 2 }

ospfNewCfgMdkeyDelete OBJECT-TYPE
    SYNTAX  INTEGER {
	other(1),
        delete(2)
	}
    MAX-ACCESS read-create
    STATUS current
    DESCRIPTION
	"When set to the value of 2 (delete), the entire row is deleted.
	 When read, other(1) is returned. Setting the value to anything
	 other than 2(delete) has no effect on the state of the row."
    ::= { ospfNewCfgMdkeyEntry 3}


ospfCurCfgIntfTable OBJECT-TYPE
    SYNTAX SEQUENCE OF OspfCurCfgIntfEntry
    MAX-ACCESS not-accessible
    STATUS current
    DESCRIPTION
      "The table of OSPF Interface configuration in the current_config."
    ::= { ospfCfg 7 }

ospfCurCfgIntfEntry OBJECT-TYPE
    SYNTAX OspfCurCfgIntfEntry
    MAX-ACCESS not-accessible
    STATUS current
    DESCRIPTION
      "Information about an OSPF Interface."
    INDEX { ospfCurCfgIntfIndex }
    ::= { ospfCurCfgIntfTable 1 }

OspfCurCfgIntfEntry ::= SEQUENCE {
    ospfCurCfgIntfIndex         Integer32,
    ospfCurCfgIntfId            IpAddress,
    ospfCurCfgIntfMdkey         INTEGER,
    ospfCurCfgIntfAreaId        INTEGER,
    ospfCurCfgIntfPriority      INTEGER,
    ospfCurCfgIntfCost          INTEGER,
    ospfCurCfgIntfHello         INTEGER,
    ospfCurCfgIntfDead          INTEGER,
    ospfCurCfgIntfTransit       INTEGER,
    ospfCurCfgIntfRetrans       INTEGER,
    ospfCurCfgIntfKey           DisplayString,
    ospfCurCfgIntfState         INTEGER
    }

ospfCurCfgIntfIndex OBJECT-TYPE
    SYNTAX Integer32
    MAX-ACCESS read-only
    STATUS current
    DESCRIPTION
	"The OSPF Interface number for which the OSPF Interface table is
         related."
    ::= { ospfCurCfgIntfEntry 1}

ospfCurCfgIntfId OBJECT-TYPE
    SYNTAX IpAddress
    MAX-ACCESS read-only
    STATUS current
    DESCRIPTION
    "The IP Address of the OSPF interface."
    ::= { ospfCurCfgIntfEntry 2 }

ospfCurCfgIntfMdkey OBJECT-TYPE
    SYNTAX INTEGER (0..255)
    MAX-ACCESS read-only
    STATUS current
    DESCRIPTION
	"The MD5 key for the OSPF interface
         0 (none) no MD5 authentication."
    ::= { ospfCurCfgIntfEntry 3 }

ospfCurCfgIntfAreaId OBJECT-TYPE
    SYNTAX INTEGER (0..2)
    MAX-ACCESS read-only
    STATUS current
    DESCRIPTION
        "Specify Area Index."
    ::= { ospfCurCfgIntfEntry 4 }

ospfCurCfgIntfPriority OBJECT-TYPE
    SYNTAX INTEGER (1..65535)
    MAX-ACCESS read-only
    STATUS current
    DESCRIPTION
        "Specify interface router priority."
    ::= { ospfCurCfgIntfEntry 5 }

ospfCurCfgIntfCost OBJECT-TYPE
    SYNTAX INTEGER (1..65535)
    MAX-ACCESS read-only
    STATUS current
    DESCRIPTION
        "Interface Cost."
    ::= { ospfCurCfgIntfEntry 6 }

ospfCurCfgIntfHello OBJECT-TYPE
    SYNTAX INTEGER (1..65535)
    MAX-ACCESS read-only
    STATUS current
    DESCRIPTION
        "Hello interval in seconds."
    ::= { ospfCurCfgIntfEntry 7 }

ospfCurCfgIntfDead OBJECT-TYPE
    SYNTAX INTEGER (1..65535)
    MAX-ACCESS read-only
    STATUS current
    DESCRIPTION
        "Dead interval in seconds."
    ::= { ospfCurCfgIntfEntry 8 }

ospfCurCfgIntfTransit OBJECT-TYPE
    SYNTAX INTEGER (0..3600)
    MAX-ACCESS read-only
    STATUS current
    DESCRIPTION
        "Transit delay in seconds."
    ::= { ospfCurCfgIntfEntry 9 }

ospfCurCfgIntfRetrans OBJECT-TYPE
    SYNTAX INTEGER (0..3600)
    MAX-ACCESS read-only
    STATUS current
    DESCRIPTION
        "Retransmit interval in seconds."
    ::= { ospfCurCfgIntfEntry 10 }

ospfCurCfgIntfKey  OBJECT-TYPE
    SYNTAX   DisplayString (SIZE(0..8))
    MAX-ACCESS  read-only
    STATUS  current
    DESCRIPTION
        "Specify Authentication Key."
    ::= { ospfCurCfgIntfEntry 11 }

ospfCurCfgIntfState OBJECT-TYPE
    SYNTAX INTEGER {
        enabled(1),
        disabled(2)
        }
    MAX-ACCESS read-only
    STATUS current
    DESCRIPTION
        "Enable or disable OSPF Interface."
    ::= { ospfCurCfgIntfEntry 12 }

ospfNewCfgIntfTable OBJECT-TYPE
    SYNTAX SEQUENCE OF OspfNewCfgIntfEntry
    MAX-ACCESS not-accessible
    STATUS current
    DESCRIPTION
      "The table of OSPF Interface configuration in the new_config."
    ::= { ospfCfg 8 }

ospfNewCfgIntfEntry OBJECT-TYPE
    SYNTAX OspfNewCfgIntfEntry
    MAX-ACCESS not-accessible
    STATUS current
    DESCRIPTION
      "Information about an OSPF Interface."
    INDEX { ospfNewCfgIntfIndex }
    ::= { ospfNewCfgIntfTable 1 }

OspfNewCfgIntfEntry ::= SEQUENCE {
    ospfNewCfgIntfIndex         Integer32,
    ospfNewCfgIntfId            IpAddress,
    ospfNewCfgIntfMdkey         INTEGER,
    ospfNewCfgIntfAreaId        INTEGER,
    ospfNewCfgIntfPriority      INTEGER,
    ospfNewCfgIntfCost          INTEGER,
    ospfNewCfgIntfHello         INTEGER,
    ospfNewCfgIntfDead          INTEGER,
    ospfNewCfgIntfTransit       INTEGER,
    ospfNewCfgIntfRetrans       INTEGER,
    ospfNewCfgIntfKey           DisplayString,
    ospfNewCfgIntfState         INTEGER,
    ospfNewCfgIntfDelete        INTEGER
    }

ospfNewCfgIntfIndex OBJECT-TYPE
    SYNTAX Integer32
    MAX-ACCESS read-only
    STATUS current
    DESCRIPTION
	"The OSPF Interface number for which the OSPF Interface table is
         related."
    ::= { ospfNewCfgIntfEntry 1}

ospfNewCfgIntfId OBJECT-TYPE
    SYNTAX IpAddress
    MAX-ACCESS read-only
    STATUS current
    DESCRIPTION
    "The IP Address of the OSPF interface."
    ::= { ospfNewCfgIntfEntry 2 }

ospfNewCfgIntfMdkey OBJECT-TYPE
    SYNTAX INTEGER (0..255)
    MAX-ACCESS read-create
    STATUS current
    DESCRIPTION
	"The MD5 key for the OSPF interface
         0 (none) no MD5 authentication."
    ::= { ospfNewCfgIntfEntry 3 }

ospfNewCfgIntfAreaId OBJECT-TYPE
    SYNTAX INTEGER (0..2)
    MAX-ACCESS read-create
    STATUS current
    DESCRIPTION
        "Specify Area Index."
    ::= { ospfNewCfgIntfEntry 4 }

ospfNewCfgIntfPriority OBJECT-TYPE
    SYNTAX INTEGER (1..65535)
    MAX-ACCESS read-create
    STATUS current
    DESCRIPTION
        "Specify interface router priority."
    ::= { ospfNewCfgIntfEntry 5 }

ospfNewCfgIntfCost OBJECT-TYPE
    SYNTAX INTEGER (1..65535)
    MAX-ACCESS read-create
    STATUS current
    DESCRIPTION
        "Specify interface cost."
    ::= { ospfNewCfgIntfEntry 6 }

ospfNewCfgIntfHello OBJECT-TYPE
    SYNTAX INTEGER (1..65535)
    MAX-ACCESS read-create
    STATUS current
    DESCRIPTION
        "Hello interval in seconds."
    ::= { ospfNewCfgIntfEntry 7 }

ospfNewCfgIntfDead OBJECT-TYPE
    SYNTAX INTEGER (1..65535)
    MAX-ACCESS read-create
    STATUS current
    DESCRIPTION
        "Dead interval in seconds."
    ::= { ospfNewCfgIntfEntry 8 }

ospfNewCfgIntfTransit OBJECT-TYPE
    SYNTAX INTEGER (0..3600)
    MAX-ACCESS read-create
    STATUS current
    DESCRIPTION
        "Transit delay in seconds."
    ::= { ospfNewCfgIntfEntry 9 }

ospfNewCfgIntfRetrans OBJECT-TYPE
    SYNTAX INTEGER (0..3600)
    MAX-ACCESS read-create
    STATUS current
    DESCRIPTION
        "Retransmit interval in seconds."
    ::= { ospfNewCfgIntfEntry 10 }

ospfNewCfgIntfKey  OBJECT-TYPE
    SYNTAX   DisplayString (SIZE(0..8))
    MAX-ACCESS  read-create
    STATUS  current
    DESCRIPTION
        "Specify Authentication Key."
    ::= { ospfNewCfgIntfEntry 11 }

ospfNewCfgIntfState OBJECT-TYPE
    SYNTAX INTEGER {
        enabled(1),
        disabled(2)
        }
    MAX-ACCESS read-create
    STATUS current
    DESCRIPTION
        "Enable or disable OSPF Interface."
    ::= { ospfNewCfgIntfEntry 12 }

ospfNewCfgIntfDelete OBJECT-TYPE
    SYNTAX  INTEGER {
        other(1),
        delete(2)
        }
    MAX-ACCESS  read-create
    STATUS  current
    DESCRIPTION
        "When set to the value of 2 (delete), the entire row is deleted.
         When read, other(1) is returned. Setting the value to anything
         other than 2(delete) has no effect on the state of the row."
    ::= { ospfNewCfgIntfEntry 13 }

ospfCurCfgVirtIntfTable OBJECT-TYPE
    SYNTAX SEQUENCE OF OspfCurCfgVirtIntfEntry
    MAX-ACCESS not-accessible
    STATUS current
    DESCRIPTION
      "The table of OSPF Virtual Interface configuration in the current
       configuration."
    ::= { ospfCfg 9 }

ospfCurCfgVirtIntfEntry OBJECT-TYPE
    SYNTAX OspfCurCfgVirtIntfEntry
    MAX-ACCESS not-accessible
    STATUS current
    DESCRIPTION
      "Information about an OSPF virtual Interface."
    INDEX { ospfCurCfgVirtIntfIndex }
    ::= { ospfCurCfgVirtIntfTable 1 }

OspfCurCfgVirtIntfEntry ::= SEQUENCE {
    ospfCurCfgVirtIntfIndex         Integer32,
    ospfCurCfgVirtIntfAreaId        INTEGER,
    ospfCurCfgVirtIntfNbr           IpAddress,
    ospfCurCfgVirtIntfMdkey         INTEGER,
    ospfCurCfgVirtIntfHello         INTEGER,
    ospfCurCfgVirtIntfDead          INTEGER,
    ospfCurCfgVirtIntfTransit       INTEGER,
    ospfCurCfgVirtIntfRetrans       INTEGER,
    ospfCurCfgVirtIntfKey           DisplayString,
    ospfCurCfgVirtIntfState         INTEGER
    }

ospfCurCfgVirtIntfIndex OBJECT-TYPE
    SYNTAX Integer32
    MAX-ACCESS read-only
    STATUS current
    DESCRIPTION
	"The OSPF Virtual Interface number for which the OSPF
         Virtual Interface table is related."
    ::= { ospfCurCfgVirtIntfEntry 1}

ospfCurCfgVirtIntfAreaId OBJECT-TYPE
    SYNTAX INTEGER (0..2)
    MAX-ACCESS read-only
    STATUS current
    DESCRIPTION
         "The OSPF Area Id."
    ::= { ospfCurCfgVirtIntfEntry 2 }

ospfCurCfgVirtIntfNbr OBJECT-TYPE
    SYNTAX IpAddress
    MAX-ACCESS read-only
    STATUS current
    DESCRIPTION
	"The IP Address of the OSPF neighbour for this virtual interface."
    ::= { ospfCurCfgVirtIntfEntry 3 }

ospfCurCfgVirtIntfMdkey OBJECT-TYPE
    SYNTAX INTEGER (0..255)
    MAX-ACCESS read-only
    STATUS current
    DESCRIPTION
	"The MD5 key for the OSPF virtual interface
         0 (none) no MD5 authentication."
    ::= { ospfCurCfgVirtIntfEntry 4 }

ospfCurCfgVirtIntfHello OBJECT-TYPE
    SYNTAX INTEGER (1..65535)
    MAX-ACCESS read-only
    STATUS current
    DESCRIPTION
        "Hello interval in seconds."
    ::= { ospfCurCfgVirtIntfEntry 5 }

ospfCurCfgVirtIntfDead OBJECT-TYPE
    SYNTAX INTEGER (1..65535)
    MAX-ACCESS read-only
    STATUS current
    DESCRIPTION
        "Dead interval in seconds."
    ::= { ospfCurCfgVirtIntfEntry 6 }

ospfCurCfgVirtIntfTransit OBJECT-TYPE
    SYNTAX INTEGER (0..3600)
    MAX-ACCESS read-only
    STATUS current
    DESCRIPTION
        "Transit delay in seconds."
    ::= { ospfCurCfgVirtIntfEntry 7 }

ospfCurCfgVirtIntfRetrans OBJECT-TYPE
    SYNTAX INTEGER (0..3600)
    MAX-ACCESS read-only
    STATUS current
    DESCRIPTION
        "Retransmit interval in seconds."
    ::= { ospfCurCfgVirtIntfEntry 8 }

ospfCurCfgVirtIntfKey  OBJECT-TYPE
    SYNTAX   DisplayString (SIZE(0..8))
    MAX-ACCESS  read-only
    STATUS  current
    DESCRIPTION
        "Specify Authentication Key."
    ::= { ospfCurCfgVirtIntfEntry 9 }

ospfCurCfgVirtIntfState OBJECT-TYPE
    SYNTAX INTEGER {
        enabled(1),
        disabled(2)
        }
    MAX-ACCESS read-only
    STATUS current
    DESCRIPTION
        "Enable or disable OSPF Interface."
    ::= { ospfCurCfgVirtIntfEntry 10 }

ospfNewCfgVirtIntfTable OBJECT-TYPE
    SYNTAX SEQUENCE OF OspfNewCfgVirtIntfEntry
    MAX-ACCESS not-accessible
    STATUS current
    DESCRIPTION
      "The table of OSPF Virtual Interface configuration in the new_config."
    ::= { ospfCfg 10 }

ospfNewCfgVirtIntfEntry OBJECT-TYPE
    SYNTAX OspfNewCfgVirtIntfEntry
    MAX-ACCESS not-accessible
    STATUS current
    DESCRIPTION
      "Information about an OSPF virtual Interface."
    INDEX { ospfNewCfgVirtIntfIndex }
    ::= { ospfNewCfgVirtIntfTable 1 }

OspfNewCfgVirtIntfEntry ::= SEQUENCE {
    ospfNewCfgVirtIntfIndex         Integer32,
    ospfNewCfgVirtIntfAreaId        INTEGER,
    ospfNewCfgVirtIntfNbr           IpAddress,
    ospfNewCfgVirtIntfMdkey         INTEGER,
    ospfNewCfgVirtIntfHello         INTEGER,
    ospfNewCfgVirtIntfDead          INTEGER,
    ospfNewCfgVirtIntfTransit       INTEGER,
    ospfNewCfgVirtIntfRetrans       INTEGER,
    ospfNewCfgVirtIntfKey           DisplayString,
    ospfNewCfgVirtIntfState         INTEGER,
    ospfNewCfgVirtIntfDelete        INTEGER
    }

ospfNewCfgVirtIntfIndex OBJECT-TYPE
    SYNTAX Integer32
    MAX-ACCESS read-only
    STATUS current
    DESCRIPTION
	"The OSPF Virtual Interface number for which the OSPF
         Virtual Interface table is related."
    ::= { ospfNewCfgVirtIntfEntry 1}

ospfNewCfgVirtIntfAreaId OBJECT-TYPE
    SYNTAX INTEGER (0..2)
    MAX-ACCESS read-create
    STATUS current
    DESCRIPTION
  	    "The OSPF Area Id."
    ::= { ospfNewCfgVirtIntfEntry 2 }

ospfNewCfgVirtIntfNbr OBJECT-TYPE
    SYNTAX IpAddress
    MAX-ACCESS read-create
    STATUS current
    DESCRIPTION
	"The IP Address of the OSPF neighbour for this virtual interface."
    ::= { ospfNewCfgVirtIntfEntry 3 }

ospfNewCfgVirtIntfMdkey OBJECT-TYPE
    SYNTAX INTEGER (0..255)
    MAX-ACCESS read-create
    STATUS current
    DESCRIPTION
	"The MD5 key for the OSPF virtual interface
         0 (none) no MD5 authentication."
    ::= { ospfNewCfgVirtIntfEntry 4 }

ospfNewCfgVirtIntfHello OBJECT-TYPE
    SYNTAX INTEGER (1..65535)
    MAX-ACCESS read-create
    STATUS current
    DESCRIPTION
        "Hello interval in seconds."
    ::= { ospfNewCfgVirtIntfEntry 5 }

ospfNewCfgVirtIntfDead OBJECT-TYPE
    SYNTAX INTEGER (1..65535)
    MAX-ACCESS read-create
    STATUS current
    DESCRIPTION
        "Dead interval in seconds."
    ::= { ospfNewCfgVirtIntfEntry 6 }

ospfNewCfgVirtIntfTransit OBJECT-TYPE
    SYNTAX INTEGER (0..3600)
    MAX-ACCESS read-create
    STATUS current
    DESCRIPTION
        "Transit delay in seconds."
    ::= { ospfNewCfgVirtIntfEntry 7 }

ospfNewCfgVirtIntfRetrans OBJECT-TYPE
    SYNTAX INTEGER (0..3600)
    MAX-ACCESS read-create
    STATUS current
    DESCRIPTION
        "Retransmit interval in seconds."
    ::= { ospfNewCfgVirtIntfEntry 8 }

ospfNewCfgVirtIntfKey  OBJECT-TYPE
    SYNTAX   DisplayString (SIZE(0..8))
    MAX-ACCESS  read-create
    STATUS  current
    DESCRIPTION
        "Specify Authentication Key.
         Enter string of 8 characters or None."
    ::= { ospfNewCfgVirtIntfEntry 9 }

ospfNewCfgVirtIntfState OBJECT-TYPE
    SYNTAX INTEGER {
        enabled(1),
        disabled(2)
        }
    MAX-ACCESS read-create
    STATUS current
    DESCRIPTION
        "Enable or disable OSPF Interface."
    ::= { ospfNewCfgVirtIntfEntry 10 }

ospfNewCfgVirtIntfDelete OBJECT-TYPE
    SYNTAX  INTEGER {
        other(1),
        delete(2)
        }
    MAX-ACCESS  read-create
    STATUS  current
    DESCRIPTION
        "When set to the value of 2 (delete), the entire row is deleted.
         When read, other(1) is returned. Setting the value to anything
         other than 2(delete) has no effect on the state of the row."
    ::= { ospfNewCfgVirtIntfEntry 11 }

-- ospf range

ospfCurCfgRangeTable OBJECT-TYPE
    SYNTAX SEQUENCE OF OspfCurCfgRangeEntry
    MAX-ACCESS not-accessible
    STATUS current
    DESCRIPTION
      "The table of OSPF summary range in the current configuration."
    ::= { ospfCfg 14 }

ospfCurCfgRangeEntry OBJECT-TYPE
    SYNTAX OspfCurCfgRangeEntry
    MAX-ACCESS not-accessible
    STATUS current
    DESCRIPTION
      "Information about an OSPF summary range."
    INDEX { ospfCurCfgRangeIndex }
    ::= { ospfCurCfgRangeTable 1 }

OspfCurCfgRangeEntry ::= SEQUENCE {
    ospfCurCfgRangeIndex            Integer32,
    ospfCurCfgRangeAddr             IpAddress,
    ospfCurCfgRangeMask             IpAddress,
    ospfCurCfgRangeAreaIndex        Integer32,
    ospfCurCfgRangeHideState        INTEGER,
    ospfCurCfgRangeState            INTEGER
    }

ospfCurCfgRangeIndex OBJECT-TYPE
    SYNTAX Integer32
    MAX-ACCESS read-only
    STATUS current
    DESCRIPTION
	"The range number for which the OSPF summary range table is related."
    ::= { ospfCurCfgRangeEntry 1}

ospfCurCfgRangeAddr OBJECT-TYPE
    SYNTAX IpAddress
    MAX-ACCESS read-only
    STATUS current
    DESCRIPTION
	"The IP Address of the range."
    ::= { ospfCurCfgRangeEntry 2 }

ospfCurCfgRangeMask OBJECT-TYPE
    SYNTAX IpAddress
    MAX-ACCESS read-only
    STATUS current
    DESCRIPTION
	"The mask of the range."
    ::= { ospfCurCfgRangeEntry 3 }

ospfCurCfgRangeAreaIndex OBJECT-TYPE
    SYNTAX Integer32
    MAX-ACCESS read-only
    STATUS current
    DESCRIPTION
        "The area index."
    ::= { ospfCurCfgRangeEntry 4 }

ospfCurCfgRangeHideState OBJECT-TYPE
    SYNTAX  INTEGER {
        enabled(1),
        disabled(2)
        }
    MAX-ACCESS  read-only
    STATUS  current
    DESCRIPTION
        "The state of the hide range."
    ::= { ospfCurCfgRangeEntry 5 }

ospfCurCfgRangeState OBJECT-TYPE
    SYNTAX  INTEGER {
        enabled(1),
        disabled(2)
        }
    MAX-ACCESS  read-only
    STATUS  current
    DESCRIPTION
        "The state of the range."
    ::= { ospfCurCfgRangeEntry 6 }

ospfNewCfgRangeTable OBJECT-TYPE
    SYNTAX SEQUENCE OF OspfNewCfgRangeEntry
    MAX-ACCESS not-accessible
    STATUS current
    DESCRIPTION
      "The table of OSPF summary range in the new configuration."
    ::= { ospfCfg 15 }

ospfNewCfgRangeEntry OBJECT-TYPE
    SYNTAX OspfNewCfgRangeEntry
    MAX-ACCESS not-accessible
    STATUS current
    DESCRIPTION
      "Information about an OSPF summary range."
    INDEX { ospfNewCfgRangeIndex }
    ::= { ospfNewCfgRangeTable 1 }

OspfNewCfgRangeEntry ::= SEQUENCE {
    ospfNewCfgRangeIndex            Integer32,
    ospfNewCfgRangeAddr             IpAddress,
    ospfNewCfgRangeMask             IpAddress,
    ospfNewCfgRangeAreaIndex        Integer32,
    ospfNewCfgRangeHideState        INTEGER,
    ospfNewCfgRangeState            INTEGER,
    ospfNewCfgRangeDelete           INTEGER
    }

ospfNewCfgRangeIndex OBJECT-TYPE
    SYNTAX Integer32
    MAX-ACCESS read-only
    STATUS current
    DESCRIPTION
	"The range number for which the OSPF summary range table is related."
    ::= { ospfNewCfgRangeEntry 1}

ospfNewCfgRangeAddr OBJECT-TYPE
    SYNTAX IpAddress
    MAX-ACCESS read-create
    STATUS current
    DESCRIPTION
	"The IP Address of the range."
    ::= { ospfNewCfgRangeEntry 2 }

ospfNewCfgRangeMask OBJECT-TYPE
    SYNTAX IpAddress
    MAX-ACCESS read-create
    STATUS current
    DESCRIPTION
	"The mask of the range."
    ::= { ospfNewCfgRangeEntry 3 }

ospfNewCfgRangeAreaIndex OBJECT-TYPE
    SYNTAX Integer32
    MAX-ACCESS read-create
    STATUS current
    DESCRIPTION
        "The area index."
    ::= { ospfNewCfgRangeEntry 4 }

ospfNewCfgRangeHideState OBJECT-TYPE
    SYNTAX  INTEGER {
        enabled(1),
        disabled(2)
        }
    MAX-ACCESS read-create
    STATUS  current
    DESCRIPTION
        "The state of the hide range."
    ::= { ospfNewCfgRangeEntry 5 }

ospfNewCfgRangeState OBJECT-TYPE
    SYNTAX  INTEGER {
        enabled(1),
        disabled(2)
        }
    MAX-ACCESS read-create
    STATUS  current
    DESCRIPTION
        "The state of the range."
    ::= { ospfNewCfgRangeEntry 6 }

ospfNewCfgRangeDelete OBJECT-TYPE
    SYNTAX  INTEGER {
        other(1),
        delete(2)
        }
    MAX-ACCESS  read-create
    STATUS  current
    DESCRIPTION
        "When set to the value of 2 (delete), the entire row is deleted.
         When read, other(1) is returned. Setting the value to anything
         other than 2(delete) has no effect on the state of the row."
    ::= { ospfNewCfgRangeEntry 7 }


ospfRouteRedistribution   OBJECT IDENTIFIER ::= { ospfCfg 4 }

ospfRedistributeStatic    OBJECT IDENTIFIER ::= { ospfRouteRedistribution 1 }

ospfCurCfgStaticMetric OBJECT-TYPE
    SYNTAX INTEGER (0..16777215)
    MAX-ACCESS read-only
    STATUS current
    DESCRIPTION
	"The metric to be assigned to static routes.
         A value of 0 indicates none."
    ::= { ospfRedistributeStatic 1 }

ospfNewCfgStaticMetric OBJECT-TYPE
    SYNTAX INTEGER (0..16777215)
    MAX-ACCESS read-write
    STATUS current
    DESCRIPTION
	"The metric to be assigned to static routes.
         A value of 0 indicates none."
    ::= { ospfRedistributeStatic 2 }

ospfCurCfgStaticMetricType OBJECT-TYPE
    SYNTAX INTEGER {
        none(1),
        type1(2),
        type2(3)
        }
    MAX-ACCESS read-only
    STATUS current
    DESCRIPTION
	"The AS External metric type for static routes."
    ::= { ospfRedistributeStatic 3 }

ospfNewCfgStaticMetricType OBJECT-TYPE
    SYNTAX INTEGER {
        none(1),
        type1(2),
        type2(3)
        }
    MAX-ACCESS read-write
    STATUS current
    DESCRIPTION
	"The AS External metric type for static routes."
    ::= { ospfRedistributeStatic 4 }

ospfCurCfgStaticOutRmapList OBJECT-TYPE
    SYNTAX OCTET STRING
    MAX-ACCESS read-only
    STATUS current
    DESCRIPTION
        "The route maps present in the out route map list.
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { ospfRedistributeStatic 5 }

ospfNewCfgStaticOutRmapList OBJECT-TYPE
    SYNTAX OCTET STRING
    MAX-ACCESS read-only
    STATUS current
    DESCRIPTION
        "The route maps present in the out route map list.
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { ospfRedistributeStatic 6 }

ospfNewCfgStaticAddOutRmap OBJECT-TYPE
    SYNTAX Integer32
    MAX-ACCESS read-write
    STATUS current
    DESCRIPTION
	"The route map to be add into out-rmap list. When read, 0 is returned."
    ::= { ospfRedistributeStatic 7 }

ospfNewCfgStaticRemoveOutRmap OBJECT-TYPE
    SYNTAX Integer32
    MAX-ACCESS read-write
    STATUS current
    DESCRIPTION
	"The route map to be removed from out-rmap list. When read,
         0 is returned."
    ::= { ospfRedistributeStatic 8 }

ospfRedistributeEbgp    OBJECT IDENTIFIER ::= { ospfRouteRedistribution 2 }

ospfCurCfgEbgpMetric OBJECT-TYPE
    SYNTAX INTEGER (0..16777215)
    MAX-ACCESS read-only
    STATUS current
    DESCRIPTION
	"The export metric to be assigned to External BGP routes.
         A value of 0 indicates none."
    ::= { ospfRedistributeEbgp 1 }

ospfNewCfgEbgpMetric OBJECT-TYPE
    SYNTAX INTEGER (0..16777215)
    MAX-ACCESS read-write
    STATUS current
    DESCRIPTION
	"The export metric to be assigned to External BGP routes.
         A value of 0 indicates none."
    ::= { ospfRedistributeEbgp 2 }

ospfCurCfgEbgpMetricType OBJECT-TYPE
    SYNTAX INTEGER {
        none(1),
        type1(2),
        type2(3)
        }
    MAX-ACCESS read-only
    STATUS current
    DESCRIPTION
	"The AS External metric type for External BGP routes."
    ::= { ospfRedistributeEbgp 3 }

ospfNewCfgEbgpMetricType OBJECT-TYPE
    SYNTAX INTEGER {
        none(1),
        type1(2),
        type2(3)
        }
    MAX-ACCESS read-write
    STATUS current
    DESCRIPTION
	"The AS External metric type for External BGP routes."
    ::= { ospfRedistributeEbgp 4 }

ospfCurCfgEbgpOutRmapList OBJECT-TYPE
    SYNTAX OCTET STRING
    MAX-ACCESS read-only
    STATUS current
    DESCRIPTION
        "The route maps present in the out route map list.
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { ospfRedistributeEbgp 5 }

ospfNewCfgEbgpOutRmapList OBJECT-TYPE
    SYNTAX OCTET STRING
    MAX-ACCESS read-only
    STATUS current
    DESCRIPTION
        "The route maps present in the out route map list.
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { ospfRedistributeEbgp 6 }

ospfNewCfgEbgpAddOutRmap OBJECT-TYPE
    SYNTAX Integer32
    MAX-ACCESS read-write
    STATUS current
    DESCRIPTION
	"The route map to be added into out-rmap list. When read, 0 is returned."
    ::= { ospfRedistributeEbgp 7 }

ospfNewCfgEbgpRemoveOutRmap OBJECT-TYPE
    SYNTAX Integer32
    MAX-ACCESS read-write
    STATUS current
    DESCRIPTION
	"The route map to be removed from out-rmap list. When read,
         0 is returned."
    ::= { ospfRedistributeEbgp 8 }

ospfRedistributeIbgp    OBJECT IDENTIFIER ::= { ospfRouteRedistribution 3 }

ospfCurCfgIbgpMetric OBJECT-TYPE
    SYNTAX INTEGER (0..16777215)
    MAX-ACCESS read-only
    STATUS current
    DESCRIPTION
	"The export metric for Internal BGP routes.
         A value of 0 indicates none."
    ::= { ospfRedistributeIbgp 1 }

ospfNewCfgIbgpMetric OBJECT-TYPE
    SYNTAX INTEGER (0..16777215)
    MAX-ACCESS read-write
    STATUS current
    DESCRIPTION
	"The export metric for Internal BGP routes.
         A value of 0 indicates none."
    ::= { ospfRedistributeIbgp 2 }

ospfCurCfgIbgpMetricType OBJECT-TYPE
    SYNTAX INTEGER {
        none(1),
        type1(2),
        type2(3)
        }
    MAX-ACCESS read-only
    STATUS current
    DESCRIPTION
	"The AS External metric type for Internal BGP routes."
    ::= { ospfRedistributeIbgp 3 }

ospfNewCfgIbgpMetricType OBJECT-TYPE
    SYNTAX INTEGER {
        none(1),
        type1(2),
        type2(3)
        }
    MAX-ACCESS read-write
    STATUS current
    DESCRIPTION
	"The AS External metric type for Internal BGP routes."
    ::= { ospfRedistributeIbgp 4 }

ospfCurCfgIbgpOutRmapList OBJECT-TYPE
    SYNTAX OCTET STRING
    MAX-ACCESS read-only
    STATUS current
    DESCRIPTION
        "The route maps present in the out route map list.
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { ospfRedistributeIbgp 5 }

ospfNewCfgIbgpOutRmapList OBJECT-TYPE
    SYNTAX OCTET STRING
    MAX-ACCESS read-only
    STATUS current
    DESCRIPTION
        "The route maps present in the out route map list.
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { ospfRedistributeIbgp 6 }

ospfNewCfgIbgpAddOutRmap OBJECT-TYPE
    SYNTAX Integer32
    MAX-ACCESS read-write
    STATUS current
    DESCRIPTION
	"The route map to be add into out-rmap list. When read, 0 is returned."
    ::= { ospfRedistributeIbgp 7 }

ospfNewCfgIbgpRemoveOutRmap OBJECT-TYPE
    SYNTAX Integer32
    MAX-ACCESS read-write
    STATUS current
    DESCRIPTION
	"The route map to be removed from out-rmap list. When read,
         0 is returned."
    ::= { ospfRedistributeIbgp 8 }

ospfRedistributeFixed    OBJECT IDENTIFIER ::= { ospfRouteRedistribution 4 }

ospfCurCfgFixedMetric OBJECT-TYPE
    SYNTAX INTEGER (0..16777215)
    MAX-ACCESS read-only
    STATUS current
    DESCRIPTION
	"The export metric for fixed routes. A value of 0 indicates none"
    ::= { ospfRedistributeFixed 1 }

ospfNewCfgFixedMetric OBJECT-TYPE
    SYNTAX INTEGER (0..16777215)
    MAX-ACCESS read-write
    STATUS current
    DESCRIPTION
	"The export metric for fixed routes. A value of 0 indicates none"
    ::= { ospfRedistributeFixed 2 }

ospfCurCfgFixedMetricType OBJECT-TYPE
    SYNTAX INTEGER {
        none(1),
        type1(2),
        type2(3)
        }
    MAX-ACCESS read-only
    STATUS current
    DESCRIPTION
	"The AS External metric type for fixed routes."
    ::= { ospfRedistributeFixed 3 }

ospfNewCfgFixedMetricType OBJECT-TYPE
    SYNTAX INTEGER {
        none(1),
        type1(2),
        type2(3)
        }
    MAX-ACCESS read-write
    STATUS current
    DESCRIPTION
	"The AS External metric type for fixed routes."
    ::= { ospfRedistributeFixed 4 }

ospfCurCfgFixedOutRmapList OBJECT-TYPE
    SYNTAX OCTET STRING
    MAX-ACCESS read-only
    STATUS current
    DESCRIPTION
        "The route maps present in the out route map list.
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { ospfRedistributeFixed 5 }

ospfNewCfgFixedOutRmapList OBJECT-TYPE
    SYNTAX OCTET STRING
    MAX-ACCESS read-only
    STATUS current
    DESCRIPTION
        "The route maps present in the out route map list.
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { ospfRedistributeFixed 6 }

ospfNewCfgFixedAddOutRmap OBJECT-TYPE
    SYNTAX Integer32
    MAX-ACCESS read-write
    STATUS current
    DESCRIPTION
	"The route map to be add into out-rmap list. When read, 0 is returned."
    ::= { ospfRedistributeFixed 7 }

ospfNewCfgFixedRemoveOutRmap OBJECT-TYPE
    SYNTAX Integer32
    MAX-ACCESS read-write
    STATUS current
    DESCRIPTION
	"The route map to be removed from out-rmap list. When read,
         0 is returned."
    ::= { ospfRedistributeFixed 8 }

ospfRedistributeRip    OBJECT IDENTIFIER ::= { ospfRouteRedistribution 5 }

ospfCurCfgRipMetric OBJECT-TYPE
    SYNTAX INTEGER (0..16777215)
    MAX-ACCESS read-only
    STATUS current
    DESCRIPTION
	"The export metric for RIP routes. A value of 0 indicates none"
    ::= { ospfRedistributeRip 1 }

ospfNewCfgRipMetric OBJECT-TYPE
    SYNTAX INTEGER (0..16777215)
    MAX-ACCESS read-write
    STATUS current
    DESCRIPTION
	"The export metric for RIP routes. A value of 0 indicates none"
    ::= { ospfRedistributeRip 2 }

ospfCurCfgRipMetricType OBJECT-TYPE
    SYNTAX INTEGER {
        none(1),
        type1(2),
        type2(3)
        }
    MAX-ACCESS read-only
    STATUS current
    DESCRIPTION
	"The AS External metric type for RIP routes."
    ::= { ospfRedistributeRip 3 }

ospfNewCfgRipMetricType OBJECT-TYPE
    SYNTAX INTEGER {
        none(1),
        type1(2),
        type2(3)
        }
    MAX-ACCESS read-write
    STATUS current
    DESCRIPTION
	"The AS External metric type for RIP routes."
    ::= { ospfRedistributeRip 4 }

ospfCurCfgRipOutRmapList OBJECT-TYPE
    SYNTAX OCTET STRING
    MAX-ACCESS read-only
    STATUS current
    DESCRIPTION
        "The route maps present in the out route map list.
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { ospfRedistributeRip 5 }

ospfNewCfgRipOutRmapList OBJECT-TYPE
    SYNTAX OCTET STRING
    MAX-ACCESS read-only
    STATUS current
    DESCRIPTION
        "The route maps present in the out route map list.
         The route maps are presented in a bitmap format.

         in receiving order:

         OCTET 1  OCTET 2  .....
         xxxxxxxx xxxxxxxx .....
         ||    || |_ Rmap 9
         ||    ||
         ||    ||___ Rmap 8
         ||    |____ Rmap 7
         ||      .    .   .
         ||_________ Rmap 2
         |__________ Rmap 1

         where x : 1 - The represented route map is selected
         0 - The represented route map is not selected"
    ::= { ospfRedistributeRip 6 }

ospfNewCfgRipAddOutRmap OBJECT-TYPE
    SYNTAX Integer32
    MAX-ACCESS read-write
    STATUS current
    DESCRIPTION
	"The route map to be add into out-rmap list. When read, 0 is returned."
    ::= { ospfRedistributeRip 7 }

ospfNewCfgRipRemoveOutRmap OBJECT-TYPE
    SYNTAX Integer32
    MAX-ACCESS read-write
    STATUS current
    DESCRIPTION
	"The route map to be removed from out-rmap list. When read,
         0 is returned."
    ::= { ospfRedistributeRip 8 }

ipCurCfgRouterID OBJECT-TYPE
    SYNTAX IpAddress
    MAX-ACCESS read-only
    STATUS current
    DESCRIPTION
	"The router ID of the switch."
    ::= { ipGeneralCfg 1 }

ipNewCfgRouterID OBJECT-TYPE
    SYNTAX IpAddress
    MAX-ACCESS read-write
    STATUS current
    DESCRIPTION
	"The router ID of the switch."
    ::= { ipGeneralCfg 2 }

ipCurCfgASNumber OBJECT-TYPE
    SYNTAX INTEGER (1..65535)
    MAX-ACCESS read-only
    STATUS current
    DESCRIPTION
	"The autonomous system (AS) number."
    ::= { ipGeneralCfg 3 }

ipNewCfgASNumber OBJECT-TYPE
    SYNTAX INTEGER (1..65535)
    MAX-ACCESS read-write
    STATUS current
    DESCRIPTION
	"The autonomous system (AS) number."
    ::= { ipGeneralCfg 4 }

--
-- IPMC Static Route Configuration
--
--
-- Static ARP Configuration
--
ipStaticArpTableMaxSize OBJECT-TYPE
    SYNTAX  Integer32
    MAX-ACCESS  read-only
    STATUS  current
    DESCRIPTION
        "The maximum number of rows in the Static ARP table."
    ::= { ipStaticArpCfg 1 }

ipCurCfgStaticArpTable OBJECT-TYPE
    SYNTAX  SEQUENCE OF IpCurCfgStaticArpEntry
    MAX-ACCESS  not-accessible
    STATUS  current
    DESCRIPTION
        "The table of static ARPs in the current configuration block."
    ::= { ipStaticArpCfg 2 }

ipCurCfgStaticArpEntry OBJECT-TYPE
    SYNTAX  IpCurCfgStaticArpEntry
    MAX-ACCESS  not-accessible
    STATUS  current
    DESCRIPTION
        "A row in the static ARP table"
    INDEX   { ipCurCfgStaticArpIndx }
    ::= { ipCurCfgStaticArpTable 1 }

IpCurCfgStaticArpEntry ::= SEQUENCE {
    ipCurCfgStaticArpIndx         Integer32,
    ipCurCfgStaticArpIp           IpAddress,
    ipCurCfgStaticArpMAC          PhysAddress,
    ipCurCfgStaticArpVlan         Integer32,
    ipCurCfgStaticArpPort         Integer32
    }

ipCurCfgStaticArpIndx OBJECT-TYPE
    SYNTAX  Integer32
    MAX-ACCESS  read-only
    STATUS  current
    DESCRIPTION
        "The index of the static ARP table."
    ::= { ipCurCfgStaticArpEntry 1}

ipCurCfgStaticArpIp OBJECT-TYPE
    SYNTAX  IpAddress
    MAX-ACCESS  read-only
    STATUS  current
    DESCRIPTION
        "The IP address for the ARP entry."
    ::= { ipCurCfgStaticArpEntry 2}

ipCurCfgStaticArpMAC OBJECT-TYPE
    SYNTAX  PhysAddress
    MAX-ACCESS  read-only
    STATUS  current
    DESCRIPTION
        "The MAC address for the ARP entry."
    ::= { ipCurCfgStaticArpEntry 3 }

ipCurCfgStaticArpVlan OBJECT-TYPE
    SYNTAX  Integer32
    MAX-ACCESS  read-only
    STATUS  current
    DESCRIPTION
        "The VLAN for the ARP entry."
    ::= { ipCurCfgStaticArpEntry 4}

ipCurCfgStaticArpPort OBJECT-TYPE
    SYNTAX  Integer32
    MAX-ACCESS  read-only
    STATUS  current
    DESCRIPTION
        "The port for the ARP entry."
    ::= { ipCurCfgStaticArpEntry 5}

ipNewCfgStaticArpTable OBJECT-TYPE
    SYNTAX  SEQUENCE OF IpNewCfgStaticArpEntry
    MAX-ACCESS  not-accessible
    STATUS  current
    DESCRIPTION
        "The table of static ARPs in the new configuration block."
    ::= { ipStaticArpCfg 3 }

ipNewCfgStaticArpEntry OBJECT-TYPE
    SYNTAX  IpNewCfgStaticArpEntry
    MAX-ACCESS  not-accessible
    STATUS  current
    DESCRIPTION
        "A row in the static ARP table"
    INDEX   { ipNewCfgStaticArpIndx }
    ::= { ipNewCfgStaticArpTable 1 }

IpNewCfgStaticArpEntry ::= SEQUENCE {
    ipNewCfgStaticArpIndx         Integer32,
    ipNewCfgStaticArpIp           IpAddress,
    ipNewCfgStaticArpMAC          PhysAddress,
    ipNewCfgStaticArpVlan         Integer32,
    ipNewCfgStaticArpPort         Integer32,
    ipNewCfgStaticArpAction       INTEGER
    }

ipNewCfgStaticArpIndx OBJECT-TYPE
    SYNTAX  Integer32
    MAX-ACCESS  read-only
    STATUS  current
    DESCRIPTION
        "The index of the static ARP table."
    ::= { ipNewCfgStaticArpEntry 1}

ipNewCfgStaticArpIp OBJECT-TYPE
    SYNTAX  IpAddress
    MAX-ACCESS  read-create
    STATUS  current
    DESCRIPTION
        "The IP address for the ARP entry."
    ::= { ipNewCfgStaticArpEntry 2}

ipNewCfgStaticArpMAC OBJECT-TYPE
    SYNTAX  PhysAddress
    MAX-ACCESS  read-create
    STATUS  current
    DESCRIPTION
        "The MAC address for the ARP entry."
    ::= { ipNewCfgStaticArpEntry 3 }

ipNewCfgStaticArpVlan OBJECT-TYPE
    SYNTAX  Integer32
    MAX-ACCESS  read-create
    STATUS  current
    DESCRIPTION
        "The VLAN for the ARP entry."
    ::= { ipNewCfgStaticArpEntry 4}

ipNewCfgStaticArpPort OBJECT-TYPE
    SYNTAX  Integer32
    MAX-ACCESS  read-create
    STATUS  current
    DESCRIPTION
        "The port for the ARP entry."
    ::= { ipNewCfgStaticArpEntry 5}

ipNewCfgStaticArpAction OBJECT-TYPE
    SYNTAX  INTEGER {
        other(1),
        delete(2)
       }
    MAX-ACCESS  read-create
    STATUS  current
    DESCRIPTION
        "When set to the value of 2 (delete), the entire row is deleted.
         When read, other is returned. Setting the value to anything other
         than 2(delete) has no effect on the state of the row."
    ::= { ipNewCfgStaticArpEntry 6 }

ipStaticArpTableNextAvailableIndex OBJECT-TYPE
    SYNTAX  Integer32
    MAX-ACCESS  read-only
    STATUS  current
    DESCRIPTION
        "The next available index in the Static ARP table."
    ::= { ipStaticArpCfg 4 }




-- Statistics

-- RIP Statistics Group


-- RIPv2 Statistics

ripStatInPackets OBJECT-TYPE
    SYNTAX  Counter32
    MAX-ACCESS  read-only
    STATUS  current
    DESCRIPTION
        "The total number of RIP packets recieved."
    ::= { rip2Stats 1 }

ripStatOutPackets OBJECT-TYPE
    SYNTAX  Counter32
    MAX-ACCESS  read-only
    STATUS  current
    DESCRIPTION
        "The total number of RIP packets transmitted."
    ::= { rip2Stats 2 }

ripStatInRequestPkts OBJECT-TYPE
    SYNTAX  Counter32
    MAX-ACCESS  read-only
    STATUS  current
    DESCRIPTION
        "The total number of RIP requests recieved."
    ::= { rip2Stats 3 }

ripStatInResponsePkts OBJECT-TYPE
    SYNTAX  Counter32
    MAX-ACCESS  read-only
    STATUS  current
    DESCRIPTION
        "The total number of RIP response recieved."
    ::= { rip2Stats 4 }

ripStatOutRequestPkts OBJECT-TYPE
    SYNTAX  Counter32
    MAX-ACCESS  read-only
    STATUS  current
    DESCRIPTION
        "The total number of RIP requests transmitted."
    ::= { rip2Stats 5 }

ripStatOutResponsePkts OBJECT-TYPE
    SYNTAX  Counter32
    MAX-ACCESS  read-only
    STATUS  current
    DESCRIPTION
        "The total number of RIP responses transmitted."
    ::= { rip2Stats 6 }

ripStatRouteTimeout OBJECT-TYPE
    SYNTAX  Counter32
    MAX-ACCESS  read-only
    STATUS  current
    DESCRIPTION
        "The total number of RIP route timeouts."
    ::= { rip2Stats 7 }

ripStatInBadSizePkts OBJECT-TYPE
    SYNTAX  Counter32
    MAX-ACCESS  read-only
    STATUS  current
    DESCRIPTION
        "The total number of bad size RIP packets recieved."
    ::= { rip2Stats 8 }

ripStatInBadVersion OBJECT-TYPE
    SYNTAX  Counter32
    MAX-ACCESS  read-only
    STATUS  current
    DESCRIPTION
        "The total number of RIP bad versions recieved."
    ::= { rip2Stats 9 }

ripStatInBadZeros OBJECT-TYPE
    SYNTAX  Counter32
    MAX-ACCESS  read-only
    STATUS  current
    DESCRIPTION
        "The total number of RIP bad zeros recieved."
    ::= { rip2Stats 10 }

ripStatInBadSourcePort OBJECT-TYPE
    SYNTAX  Counter32
    MAX-ACCESS  read-only
    STATUS  current
    DESCRIPTION
        "The total number of RIP bad source port recieved."
    ::= { rip2Stats 11 }

ripStatInBadSourceIP OBJECT-TYPE
    SYNTAX  Counter32
    MAX-ACCESS  read-only
    STATUS  current
    DESCRIPTION
        "The total number of RIP bad source IP recieved."
    ::= { rip2Stats 12 }

ripStatInSelfRcvPkts OBJECT-TYPE
    SYNTAX  Counter32
    MAX-ACCESS  read-only
    STATUS  current
    DESCRIPTION
        "The total number of RIP packets from self received."
    ::= { rip2Stats 13 }

-- TCP Statistics Group

tcpStatCurConn OBJECT-TYPE
    SYNTAX  Counter32
    MAX-ACCESS  read-only
    STATUS  current
    DESCRIPTION
        "The total number of outstanding TCP sessions that are currently opened."
    ::= { tcpStats 1 }

tcpStatCurInConn OBJECT-TYPE
    SYNTAX  Counter32
    MAX-ACCESS  read-only
    STATUS  current
    DESCRIPTION
        "The total number of remotely-initiated TCP connections."
    ::= { tcpStats 2 }

tcpStatCurOutConn OBJECT-TYPE
    SYNTAX  Counter32
    MAX-ACCESS  read-only
    STATUS  current
    DESCRIPTION
        "The total number of switch-originated TCP connection requests."
    ::= { tcpStats 3 }

-- ARP Statistics Group

arpStatEntries OBJECT-TYPE
    SYNTAX  Gauge32
    MAX-ACCESS  read-only
    STATUS  current
    DESCRIPTION
        "The current number of ARP entries."
    ::= { arpStats 1 }

arpStatHighWater OBJECT-TYPE
    SYNTAX  Gauge32
    MAX-ACCESS  read-only
    STATUS  current
    DESCRIPTION
        "The highest number of ARP entries."
    ::= { arpStats 2 }

arpStatMaxEntries OBJECT-TYPE
    SYNTAX  Gauge32
    MAX-ACCESS  read-only
    STATUS  current
    DESCRIPTION
        "The maximum number of ARP entries."
    ::= { arpStats 3 }

-- ROUTE Statistics Group

routeStatEntries OBJECT-TYPE
    SYNTAX  Gauge32
    MAX-ACCESS  read-only
    STATUS  current
    DESCRIPTION
        "The current number of IP routes."
    ::= { routeStats 1 }

routeStatHighWater OBJECT-TYPE
    SYNTAX  Gauge32
    MAX-ACCESS  read-only
    STATUS  current
    DESCRIPTION
        "The highest number of IP routes."
    ::= { routeStats 2 }

routeStatMaxEntries OBJECT-TYPE
    SYNTAX  Gauge32
    MAX-ACCESS  read-only
    STATUS  current
    DESCRIPTION
        "The maximum number of IP routes."
    ::= { routeStats 3 }

-- DNS Statistics

dnsStatInGoodDnsRequests OBJECT-TYPE
    SYNTAX  Counter32
    MAX-ACCESS  read-only
    STATUS  current
    DESCRIPTION
        "The total number of DNS request packets which are received."
    ::= { dnsStats 1 }

dnsStatInBadDnsRequests OBJECT-TYPE
    SYNTAX  Counter32
    MAX-ACCESS  read-only
    STATUS  current
    DESCRIPTION
        "The total number of DNS request packets received that were dropped."
    ::= { dnsStats 2 }

dnsStatOutDnsRequests OBJECT-TYPE
    SYNTAX  Counter32
    MAX-ACCESS  read-only
    STATUS  current
    DESCRIPTION
        "The total number of DNS response packets that have been transmitted."
    ::= { dnsStats 3 }

-- The VRRP Statistics

vrrpStatInAdvers OBJECT-TYPE
    SYNTAX  Counter32
    MAX-ACCESS  read-only
    STATUS  current
    DESCRIPTION
        "The number of good VRRP advertisements which are received."
    ::= { vrrpStats 1 }

vrrpStatOutAdvers OBJECT-TYPE
    SYNTAX  Counter32
    MAX-ACCESS  read-only
    STATUS  current
    DESCRIPTION
        "The number of good VRRP advertisements which are transmitted."
    ::= { vrrpStats 2 }

vrrpStatOutBadAdvers OBJECT-TYPE
    SYNTAX  Counter32
    MAX-ACCESS  read-only
    STATUS  current
    DESCRIPTION
        "The number of bad VRRP advertisements which are received."
    ::= { vrrpStats 3 }

-- Clear Statistics  for ip and ip interface
ipClearStats OBJECT-TYPE
    SYNTAX  INTEGER {
	ok(1),
	clear(2)
	}
    MAX-ACCESS  read-write
    STATUS  current
    DESCRIPTION
        "Setting this to clear(2) results in clearing the IP statistics."
    ::= { clearStats 1 }

ifStatsTable OBJECT-TYPE
    SYNTAX SEQUENCE OF IfStatsEntry
    MAX-ACCESS not-accessible
    STATUS current
    DESCRIPTION
      "The table of Interface Statistics."
    ::= { clearStats 2 }

ifStatsEntry OBJECT-TYPE
    SYNTAX IfStatsEntry
    MAX-ACCESS not-accessible
    STATUS current
    DESCRIPTION
      "IP Interface statistics."
    INDEX { ifStatsIndex }
    ::= { ifStatsTable 1 }

IfStatsEntry ::= SEQUENCE {
    ifStatsIndex               Integer32,
    ifClearStats               INTEGER
    }

ifStatsIndex OBJECT-TYPE
    SYNTAX  Integer32
    MAX-ACCESS  read-only
    STATUS  current
    DESCRIPTION
        "The index of the IP interface for which these statistics apply."
    ::= { ifStatsEntry 1 }

ifClearStats OBJECT-TYPE
    SYNTAX  INTEGER {
	ok(1),
	clear(2)
	}
    MAX-ACCESS  read-write
    STATUS  current
    DESCRIPTION
        "Setting this to clear(2) results in clearing the statistics for this
         IP interface (if) stats."
    ::= { ifStatsEntry 2 }

-- Ospf Statistics

-- Ospf Statistics for all interfaces and OSPF areas
ospfGeneralStats       OBJECT IDENTIFIER ::= { ospfStats  1 }
ospfCumRxTxStats       OBJECT IDENTIFIER ::= { ospfGeneralStats  1 }
ospfCumNbrChangeStats  OBJECT IDENTIFIER ::= { ospfGeneralStats  2 }
ospfCumIntfChangeStats OBJECT IDENTIFIER ::= { ospfGeneralStats  3 }
ospfTimersKickOffStats OBJECT IDENTIFIER ::= { ospfGeneralStats  4 }

-- Ospf Statistics / Area
ospfArea	       OBJECT IDENTIFIER ::= { ospfStats  2 }

ospfAreaRxTxStats OBJECT-TYPE
    SYNTAX SEQUENCE OF OspfAreaRxTxStatsEntry
    MAX-ACCESS not-accessible
    STATUS current
    DESCRIPTION
      "The table of OSPF Area Rx/Tx Statistics."
    ::= { ospfArea 1 }

ospfAreaRxTxStatsEntry OBJECT-TYPE
    SYNTAX OspfAreaRxTxStatsEntry
    MAX-ACCESS not-accessible
    STATUS current
    DESCRIPTION
      "Rx Tx packet Statistics about a OSPF area."
    INDEX { ospfAreaRxTxIndex }
    ::= { ospfAreaRxTxStats 1 }

OspfAreaRxTxStatsEntry ::= SEQUENCE {
    ospfAreaRxTxIndex          Integer32,
    ospfAreaRxPkts             Counter32,
    ospfAreaTxPkts             Counter32,
    ospfAreaRxHello            Counter32,
    ospfAreaTxHello            Counter32,
    ospfAreaRxDatabase         Counter32,
    ospfAreaTxDatabase         Counter32,
    ospfAreaRxlsReqs           Counter32,
    ospfAreaTxlsReqs           Counter32,
    ospfAreaRxlsAcks           Counter32,
    ospfAreaTxlsAcks           Counter32,
    ospfAreaRxlsUpdates        Counter32,
    ospfAreaTxlsUpdates        Counter32
    }

ospfAreaRxTxIndex OBJECT-TYPE
    SYNTAX  Integer32
    MAX-ACCESS  read-only
    STATUS  current
    DESCRIPTION
        "The index of the ospf Area for which these statistics apply."
    ::= { ospfAreaRxTxStatsEntry 1 }

ospfAreaRxPkts OBJECT-TYPE
    SYNTAX  Counter32
    MAX-ACCESS  read-only
    STATUS  current
    DESCRIPTION
        "The total number of OSPF packets received in this OSPF area."
    ::= { ospfAreaRxTxStatsEntry 2 }

ospfAreaTxPkts OBJECT-TYPE
    SYNTAX  Counter32
    MAX-ACCESS  read-only
    STATUS  current
    DESCRIPTION
        "The total number of OSPF packets transmitted in this OSPF area."
    ::= { ospfAreaRxTxStatsEntry 3 }

ospfAreaRxHello OBJECT-TYPE
    SYNTAX  Counter32
    MAX-ACCESS  read-only
    STATUS  current
    DESCRIPTION
        "The total number of Hello packets received in this OSPF area."
    ::= { ospfAreaRxTxStatsEntry 4 }

ospfAreaTxHello OBJECT-TYPE
    SYNTAX  Counter32
    MAX-ACCESS  read-only
    STATUS  current
    DESCRIPTION
        "The total number of Hello packets transmitted in this OSPF
         area."
    ::= { ospfAreaRxTxStatsEntry 5 }

ospfAreaRxDatabase OBJECT-TYPE
    SYNTAX  Counter32
    MAX-ACCESS  read-only
    STATUS  current
    DESCRIPTION
        "The total number of Database Description packets transmitted
         for this OSPF area."
    ::= { ospfAreaRxTxStatsEntry 6 }

ospfAreaTxDatabase OBJECT-TYPE
    SYNTAX  Counter32
    MAX-ACCESS  read-only
    STATUS  current
    DESCRIPTION
        "The total number of Database Description packets transmitted
         for this OSPF area."
    ::= { ospfAreaRxTxStatsEntry 7 }

ospfAreaRxlsReqs OBJECT-TYPE
    SYNTAX  Counter32
    MAX-ACCESS  read-only
    STATUS  current
    DESCRIPTION
        "The total number of Link State Request packets received for
         this OSPF area."
    ::= { ospfAreaRxTxStatsEntry 8 }

ospfAreaTxlsReqs OBJECT-TYPE
    SYNTAX  Counter32
    MAX-ACCESS  read-only
    STATUS  current
    DESCRIPTION
        "The total number of Link State Request packets transmitted for
         this OSPF area."
    ::= { ospfAreaRxTxStatsEntry 9 }

ospfAreaRxlsAcks OBJECT-TYPE
    SYNTAX  Counter32
    MAX-ACCESS  read-only
    STATUS  current
    DESCRIPTION
        "The total number of Link State Acknowledgement packets received for
         this OSPF area."
    ::= { ospfAreaRxTxStatsEntry 10 }

ospfAreaTxlsAcks OBJECT-TYPE
    SYNTAX  Counter32
    MAX-ACCESS  read-only
    STATUS  current
    DESCRIPTION
        "The total number of Link State Acknowledgement packets transmitted
         for this OSPF area."
    ::= { ospfAreaRxTxStatsEntry 11 }

ospfAreaRxlsUpdates OBJECT-TYPE
    SYNTAX  Counter32
    MAX-ACCESS  read-only
    STATUS  current
    DESCRIPTION
        "The total number of Link State Update packets received for
         this OSPF area."
    ::= { ospfAreaRxTxStatsEntry 12 }

ospfAreaTxlsUpdates OBJECT-TYPE
    SYNTAX  Counter32
    MAX-ACCESS  read-only
    STATUS  current
    DESCRIPTION
        "The total number of Link State Update packets transmitted for
         this OSPF area."
    ::= { ospfAreaRxTxStatsEntry 13 }


ospfAreaNbrChangeStats OBJECT-TYPE
    SYNTAX SEQUENCE OF OspfAreaNbrChangeStatsEntry
    MAX-ACCESS not-accessible
    STATUS current
    DESCRIPTION
      "The table of OSPF Area Neighbour Statistics."
    ::= { ospfArea 2 }

ospfAreaNbrChangeStatsEntry OBJECT-TYPE
    SYNTAX OspfAreaNbrChangeStatsEntry
    MAX-ACCESS not-accessible
    STATUS current
    DESCRIPTION
      "Area Neighbour Change Statistics about a OSPF area."
    INDEX { ospfAreaNbrIndex }
    ::= { ospfAreaNbrChangeStats 1 }

OspfAreaNbrChangeStatsEntry ::= SEQUENCE {
    ospfAreaNbrIndex  	       	Integer32,
    ospfAreaNbrhello           	Counter32,
    ospfAreaNbrStart           	Counter32,
    ospfAreaNbrAdjointOk       	Counter32,
    ospfAreaNbrNegotiationDone 	Counter32,
    ospfAreaNbrExchangeDone     Counter32,
    ospfAreaNbrBadRequests      Counter32,
    ospfAreaNbrBadSequence      Counter32,
    ospfAreaNbrLoadingDone      Counter32,
    ospfAreaNbrN1way        	Counter32,
    ospfAreaNbrRstAd        	Counter32,
    ospfAreaNbrDown        	Counter32,
    ospfAreaNbrN2way           	Counter32
    }

ospfAreaNbrIndex OBJECT-TYPE
    SYNTAX  Integer32
    MAX-ACCESS  read-only
    STATUS  current
    DESCRIPTION
        "The index of the ospf Area for which these statistics apply."
    ::= { ospfAreaNbrChangeStatsEntry 1 }

ospfAreaNbrhello OBJECT-TYPE
    SYNTAX  Counter32
    MAX-ACCESS  read-only
    STATUS  current
    DESCRIPTION
        "The total number of Hello packets received from neighbours
         in this OSPF area."
    ::= { ospfAreaNbrChangeStatsEntry 2 }

ospfAreaNbrStart OBJECT-TYPE
    SYNTAX  Counter32
    MAX-ACCESS  read-only
    STATUS  current
    DESCRIPTION
        "The total number of neighbours in this state (i.e. an indication
         that  Hello packets should now be sent to the neighbour at intervals
         of HelloInterval seconds.) in this OSPF area."
    ::= { ospfAreaNbrChangeStatsEntry 3 }

ospfAreaNbrAdjointOk OBJECT-TYPE
    SYNTAX  Counter32
    MAX-ACCESS  read-only
    STATUS  current
    DESCRIPTION
        "The total number of decisions to be made (again) as to whether
         an adjacency should be established/maintained with the neighbour.
         for this OSPF area."
    ::= { ospfAreaNbrChangeStatsEntry 4 }

ospfAreaNbrNegotiationDone OBJECT-TYPE
    SYNTAX  Counter32
    MAX-ACCESS  read-only
    STATUS  current
    DESCRIPTION
        "The total number of neighbours in this state wherein the
         Master/slave relationship has been negotiated, and sequence
         numbers have been exchanged, for this OSPF area."
    ::= { ospfAreaNbrChangeStatsEntry 5 }

ospfAreaNbrExchangeDone OBJECT-TYPE
    SYNTAX  Counter32
    MAX-ACCESS  read-only
    STATUS  current
    DESCRIPTION
        "The total number of neighbours in this state (i.e. in an
         adjacency's final state) having transimitted a full sequence
         of Database Description packets, for this OSPF area."
    ::= { ospfAreaNbrChangeStatsEntry 6 }

ospfAreaNbrBadRequests OBJECT-TYPE
    SYNTAX  Counter32
    MAX-ACCESS  read-only
    STATUS  current
    DESCRIPTION
        "The sum total number of Link State Requests which have been received
         for a link state advertisement not contained in the database across
         this OSPF area."
    ::= { ospfAreaNbrChangeStatsEntry 7 }

ospfAreaNbrBadSequence OBJECT-TYPE
    SYNTAX  Counter32
    MAX-ACCESS  read-only
    STATUS  current
    DESCRIPTION
        "The total number of Database Description packets which have been
         received that either
         a) has an unexpected DD sequence number
         b) Unexpectedly has the init bit set
         c) Has an options field differing from the last Options field
            received in a Database Description packet.
         Any of these conditions indicate that some error has occured during
         adjacency establishment for this OSPF area."
    ::= { ospfAreaNbrChangeStatsEntry 8 }

ospfAreaNbrLoadingDone OBJECT-TYPE
    SYNTAX  Counter32
    MAX-ACCESS  read-only
    STATUS  current
    DESCRIPTION
        "The total number of link state updates received for all
         out-of-date portions of the database in this OSPF area."
    ::= { ospfAreaNbrChangeStatsEntry 9 }

ospfAreaNbrN1way OBJECT-TYPE
    SYNTAX  Counter32
    MAX-ACCESS  read-only
    STATUS  current
    DESCRIPTION
        "The total number of Hello packets received from neighbours, in
         which this router is not mentioned in this OSPF area."
    ::= { ospfAreaNbrChangeStatsEntry 10 }

ospfAreaNbrRstAd OBJECT-TYPE
    SYNTAX  Counter32
    MAX-ACCESS  read-only
    STATUS  current
    DESCRIPTION
        "The total number of times the Neighbour adjacency has been reset
         across this OPSF area."
    ::= { ospfAreaNbrChangeStatsEntry 11 }

ospfAreaNbrDown OBJECT-TYPE
    SYNTAX  Counter32
    MAX-ACCESS  read-only
    STATUS  current
    DESCRIPTION
        "The total number of Neighbouring routers down (i.e. in the initial
         state of a neighbour conversation.) in this OSPF area."
    ::= { ospfAreaNbrChangeStatsEntry 12 }

ospfAreaNbrN2way OBJECT-TYPE
    SYNTAX  Counter32
    MAX-ACCESS  read-only
    STATUS  current
    DESCRIPTION
        "The total number of Hello packets received from neighbours, in
         which this router is mentioned in this OSPF area."
    ::= { ospfAreaNbrChangeStatsEntry 13 }

ospfAreaChangeStats OBJECT-TYPE
    SYNTAX SEQUENCE OF OspfAreaChangeStatsEntry
    MAX-ACCESS not-accessible
    STATUS current
    DESCRIPTION
      "The table of OSPF Area Change Statistics."
    ::= { ospfArea 3 }

ospfAreaChangeStatsEntry OBJECT-TYPE
    SYNTAX OspfAreaChangeStatsEntry
    MAX-ACCESS not-accessible
    STATUS current
    DESCRIPTION
      "Area  Change Statistics about a OSPF area."
    INDEX { ospfAreaIntfIndex }
    ::= { ospfAreaChangeStats 1 }

OspfAreaChangeStatsEntry ::= SEQUENCE {
    ospfAreaIntfIndex     	Integer32,
    ospfAreaIntfHello           Counter32,
    ospfAreaIntfDown           	Counter32,
    ospfAreaIntfLoop       	Counter32,
    ospfAreaIntfUnloop 		Counter32,
    ospfAreaIntfWaitTimer     	Counter32,
    ospfAreaIntfBackup	        Counter32,
    ospfAreaIntfNbrChange       Counter32
    }

ospfAreaIntfIndex OBJECT-TYPE
    SYNTAX    Integer32
    MAX-ACCESS    read-only
    STATUS    current
    DESCRIPTION
        "The index of the OSPF Area for which these statistics apply."
    ::= { ospfAreaChangeStatsEntry 1 }

ospfAreaIntfHello OBJECT-TYPE
    SYNTAX    Counter32
    MAX-ACCESS    read-only
    STATUS    current
    DESCRIPTION
        "The total number of Hello packets sent on this OSPF area."
    ::= { ospfAreaChangeStatsEntry 2 }

ospfAreaIntfDown OBJECT-TYPE
    SYNTAX   Counter32
    MAX-ACCESS   read-only
    STATUS   current
    DESCRIPTION
        "The total number of interfaces down in this OSPF area."
    ::= { ospfAreaChangeStatsEntry 3 }

ospfAreaIntfLoop OBJECT-TYPE
    SYNTAX    Counter32
    MAX-ACCESS    read-only
    STATUS    current
    DESCRIPTION
        "The total number of interfaces no longer connected to
         the attatched network in this OSPF area."
    ::= { ospfAreaChangeStatsEntry 4 }

ospfAreaIntfUnloop OBJECT-TYPE
    SYNTAX   Counter32
    MAX-ACCESS   read-only
    STATUS   current
    DESCRIPTION
        "The total number of interfaces connected to the attatched
	 network in this OSPF area.."
    ::= { ospfAreaChangeStatsEntry 5 }


ospfAreaIntfWaitTimer OBJECT-TYPE
    SYNTAX        Counter32
    MAX-ACCESS        read-only
    STATUS        current
    DESCRIPTION
        "The total number of times the Wait Timer has been fired,
         (indicating the end of the waiting period that is required
          before electing a (Backup) Designated Router) for this
          OSPF area."
    ::= { ospfAreaChangeStatsEntry 6 }

ospfAreaIntfBackup OBJECT-TYPE
    SYNTAX     Counter32
    MAX-ACCESS     read-only
    STATUS     current
    DESCRIPTION
        "The total number of Backup Designated Routers on the attatched
         network for this OSPF area."
    ::= { ospfAreaChangeStatsEntry 7 }


ospfAreaIntfNbrChange OBJECT-TYPE
    SYNTAX     Counter32
    MAX-ACCESS     read-only
    STATUS     current
    DESCRIPTION
        "The total number of changes in the set of bidirectional neighbours
         associated with the interface in this OSPF area."
    ::= { ospfAreaChangeStatsEntry 8 }

ospfAreaErrorStats OBJECT-TYPE
    SYNTAX SEQUENCE OF OspfAreaErrorStatsEntry
    MAX-ACCESS not-accessible
    STATUS current
    DESCRIPTION
      "The table of OSPF Area Error Statistics."
    ::= { ospfArea 4 }

ospfAreaErrorStatsEntry OBJECT-TYPE
    SYNTAX OspfAreaErrorStatsEntry
    MAX-ACCESS not-accessible
    STATUS current
    DESCRIPTION
      "Error Statistics for an OSPF area."
    INDEX { ospfAreaErrIndex }
    ::= { ospfAreaErrorStats 1 }

OspfAreaErrorStatsEntry ::= SEQUENCE {
    ospfAreaErrIndex     	Integer32,
    ospfAreaErrAuthFailure      Counter32,
    ospfAreaErrNetmaskMismatch  Counter32,
    ospfAreaErrHelloMismatch    Counter32,
    ospfAreaErrDeadMismatch     Counter32,
    ospfAreaErrOptionsMismatch  Counter32,
    ospfAreaErrUnknownNbr       Counter32
    }

ospfAreaErrIndex OBJECT-TYPE
    SYNTAX    Integer32
    MAX-ACCESS    read-only
    STATUS    current
    DESCRIPTION
        "The index of the OSPF Area for which these statistics apply."
    ::= { ospfAreaErrorStatsEntry 1 }

ospfAreaErrAuthFailure OBJECT-TYPE
    SYNTAX    Counter32
    MAX-ACCESS    read-only
    STATUS    current
    DESCRIPTION
        "The total number of packets received with a wrong password in
         this area."
    ::= { ospfAreaErrorStatsEntry 2 }

ospfAreaErrNetmaskMismatch OBJECT-TYPE
    SYNTAX    Counter32
    MAX-ACCESS    read-only
    STATUS    current
    DESCRIPTION
        "The total number of packets received with a wrong netmask in
         this area."
    ::= { ospfAreaErrorStatsEntry 3 }

ospfAreaErrHelloMismatch OBJECT-TYPE
    SYNTAX    Counter32
    MAX-ACCESS    read-only
    STATUS    current
    DESCRIPTION
        "The total number of packets received with a different hello interval
         in this area."
    ::= { ospfAreaErrorStatsEntry 4 }

ospfAreaErrDeadMismatch OBJECT-TYPE
    SYNTAX    Counter32
    MAX-ACCESS    read-only
    STATUS    current
    DESCRIPTION
        "The total number of packets received with a different dead interval
         in this area."
    ::= { ospfAreaErrorStatsEntry 5 }

ospfAreaErrOptionsMismatch OBJECT-TYPE
    SYNTAX    Counter32
    MAX-ACCESS    read-only
    STATUS    current
    DESCRIPTION
        "The total number of packets received with a different options
         in this area."
    ::= { ospfAreaErrorStatsEntry 6 }

ospfAreaErrUnknownNbr OBJECT-TYPE
    SYNTAX    Counter32
    MAX-ACCESS    read-only
    STATUS    current
    DESCRIPTION
        "The total number of packets received from an unknown neighbour
         in this area."
    ::= { ospfAreaErrorStatsEntry 7 }

-- Ospf Statistics / Interface
ospfInterface	       OBJECT IDENTIFIER ::= { ospfStats  3 }

ospfIntfRxTxStats OBJECT-TYPE
    SYNTAX SEQUENCE OF OspfIntfRxTxStatsEntry
    MAX-ACCESS not-accessible
    STATUS current
    DESCRIPTION
      "The table of OSPF Interface Rx/Tx packet Statistics."
    ::= { ospfInterface 1 }

ospfIntfRxTxStatsEntry OBJECT-TYPE
    SYNTAX OspfIntfRxTxStatsEntry
    MAX-ACCESS not-accessible
    STATUS current
    DESCRIPTION
      "OSPF interface Rx/Tx packet statistics."
    INDEX { ospfIntfRxTxIndex }
    ::= { ospfIntfRxTxStats 1 }

OspfIntfRxTxStatsEntry ::= SEQUENCE {
    ospfIntfRxTxIndex          Integer32,
    ospfIntfRxPkts             Counter32,
    ospfIntfTxPkts             Counter32,
    ospfIntfRxHello            Counter32,
    ospfIntfTxHello            Counter32,
    ospfIntfRxDatabase         Counter32,
    ospfIntfTxDatabase         Counter32,
    ospfIntfRxlsReqs           Counter32,
    ospfIntfTxlsReqs           Counter32,
    ospfIntfRxlsAcks           Counter32,
    ospfIntfTxlsAcks           Counter32,
    ospfIntfRxlsUpdates        Counter32,
    ospfIntfTxlsUpdates        Counter32
    }

ospfIntfRxTxIndex OBJECT-TYPE
    SYNTAX  Integer32
    MAX-ACCESS  read-only
    STATUS  current
    DESCRIPTION
        "The OSPF interface for which these statistics apply."
    ::= { ospfIntfRxTxStatsEntry 1 }

ospfIntfRxPkts OBJECT-TYPE
    SYNTAX  Counter32
    MAX-ACCESS  read-only
    STATUS  current
    DESCRIPTION
        "The total number of OSPF packets received for this OSPF interface."
    ::= { ospfIntfRxTxStatsEntry 2 }

ospfIntfTxPkts OBJECT-TYPE
    SYNTAX  Counter32
    MAX-ACCESS  read-only
    STATUS  current
    DESCRIPTION
        "The total number of OSPF packets transmitted for this OSPF interface."
    ::= { ospfIntfRxTxStatsEntry 3 }

ospfIntfRxHello OBJECT-TYPE
    SYNTAX  Counter32
    MAX-ACCESS  read-only
    STATUS  current
    DESCRIPTION
        "The total number of Hello packets received
         for this OSPF interface."
    ::= { ospfIntfRxTxStatsEntry 4 }

ospfIntfTxHello OBJECT-TYPE
    SYNTAX  Counter32
    MAX-ACCESS  read-only
    STATUS  current
    DESCRIPTION
        "The total number of Hello packets transmitted
         for this OSPF interface."
    ::= { ospfIntfRxTxStatsEntry 5 }

ospfIntfRxDatabase OBJECT-TYPE
    SYNTAX  Counter32
    MAX-ACCESS  read-only
    STATUS  current
    DESCRIPTION
        "The total number of Database Description packets received
         for this OSPF interface."
    ::= { ospfIntfRxTxStatsEntry 6 }

ospfIntfTxDatabase OBJECT-TYPE
    SYNTAX  Counter32
    MAX-ACCESS  read-only
    STATUS  current
    DESCRIPTION
        "The total number of Database Description packets transmitted
         for this OSPF interface."
    ::= { ospfIntfRxTxStatsEntry 7 }

ospfIntfRxlsReqs OBJECT-TYPE
    SYNTAX  Counter32
    MAX-ACCESS  read-only
    STATUS  current
    DESCRIPTION
        "The total number of Link State Request packets received
         for this OSPF interface."
    ::= { ospfIntfRxTxStatsEntry 8 }

ospfIntfTxlsReqs OBJECT-TYPE
    SYNTAX  Counter32
    MAX-ACCESS  read-only
    STATUS  current
    DESCRIPTION
        "The total number of Link State Request packets transmitted
         for this OSPF interface."
    ::= { ospfIntfRxTxStatsEntry 9 }

ospfIntfRxlsAcks OBJECT-TYPE
    SYNTAX  Counter32
    MAX-ACCESS  read-only
    STATUS  current
    DESCRIPTION
        "The total number of Link State Acknowledgement packets received
         for this OSPF interface."
    ::= { ospfIntfRxTxStatsEntry 10 }

ospfIntfTxlsAcks OBJECT-TYPE
    SYNTAX  Counter32
    MAX-ACCESS  read-only
    STATUS  current
    DESCRIPTION
        "The total number of Link State Acknowledgement packets transmitted
         for this OSPF interface."
    ::= { ospfIntfRxTxStatsEntry 11 }

ospfIntfRxlsUpdates OBJECT-TYPE
    SYNTAX  Counter32
    MAX-ACCESS  read-only
    STATUS  current
    DESCRIPTION
        "The total number of Link State Update packets received for
         this OSPF interface."
    ::= { ospfIntfRxTxStatsEntry 12 }

ospfIntfTxlsUpdates OBJECT-TYPE
    SYNTAX  Counter32
    MAX-ACCESS  read-only
    STATUS  current
    DESCRIPTION
        "The total number of Link State Update packets transmitted for
         this OSPF interface."
    ::= { ospfIntfRxTxStatsEntry 13 }


ospfIntfNbrChangeStats OBJECT-TYPE
    SYNTAX SEQUENCE OF OspfIntfNbrChangeStatsEntry
    MAX-ACCESS not-accessible
    STATUS current
    DESCRIPTION
      "The table of OSPF Interface Neighbour change Statistics."
    ::= { ospfInterface 2 }

ospfIntfNbrChangeStatsEntry OBJECT-TYPE
    SYNTAX OspfIntfNbrChangeStatsEntry
    MAX-ACCESS not-accessible
    STATUS current
    DESCRIPTION
      "OSPF interface Neighbour Change statistics."
    INDEX { ospfIntfNbrIndex }
    ::= { ospfIntfNbrChangeStats 1 }

OspfIntfNbrChangeStatsEntry ::= SEQUENCE {
    ospfIntfNbrIndex     	Integer32,
    ospfIntfNbrhello           	Counter32,
    ospfIntfNbrStart           	Counter32,
    ospfIntfNbrAdjointOk       	Counter32,
    ospfIntfNbrNegotiationDone 	Counter32,
    ospfIntfNbrExchangeDone     Counter32,
    ospfIntfNbrBadRequests      Counter32,
    ospfIntfNbrBadSequence      Counter32,
    ospfIntfNbrLoadingDone      Counter32,
    ospfIntfNbrN1way        	Counter32,
    ospfIntfNbrRstAd        	Counter32,
    ospfIntfNbrDown        	Counter32,
    ospfIntfNbrN2way        	Counter32
    }

ospfIntfNbrIndex OBJECT-TYPE
    SYNTAX  Integer32
    MAX-ACCESS  read-only
    STATUS  current
    DESCRIPTION
        "The index of the OSPF Interface for which these statistics apply."
    ::= { ospfIntfNbrChangeStatsEntry 1 }

ospfIntfNbrhello OBJECT-TYPE
    SYNTAX  Counter32
    MAX-ACCESS  read-only
    STATUS  current
    DESCRIPTION
        "The total number of Hello packets received from neighbours
         in this OSPF interface."
    ::= { ospfIntfNbrChangeStatsEntry 2 }

ospfIntfNbrStart OBJECT-TYPE
    SYNTAX  Counter32
    MAX-ACCESS  read-only
    STATUS  current
    DESCRIPTION
        "The total number of neighbours in this state (i.e. an indication
         that  Hello packets should now be sent to the neighbour at intervals
         of HelloInterval seconds.) in this OSPF interface."
    ::= { ospfIntfNbrChangeStatsEntry  3 }

ospfIntfNbrAdjointOk OBJECT-TYPE
    SYNTAX  Counter32
    MAX-ACCESS  read-only
    STATUS  current
    DESCRIPTION
        "The total number of decisions to be made (again) as to whether
         an adjacency should be established/maintained with the neighbour.
         for this OSPF interface."
    ::= { ospfIntfNbrChangeStatsEntry 4 }

ospfIntfNbrNegotiationDone OBJECT-TYPE
    SYNTAX  Counter32
    MAX-ACCESS  read-only
    STATUS  current
    DESCRIPTION
        "The total number of neighbours in this state wherein the
         Master/slave relationship has been negotiated, and sequence
         numbers have been exchanged, for this OSPF interface."
    ::= { ospfIntfNbrChangeStatsEntry 5 }

ospfIntfNbrExchangeDone OBJECT-TYPE
    SYNTAX  Counter32
    MAX-ACCESS  read-only
    STATUS  current
    DESCRIPTION
        "The total number of neighbours in this state (i.e. in an
         adjacency's final state) having transimitted a full sequence
         of Database Description packets, for this OSPF interface."
    ::= { ospfIntfNbrChangeStatsEntry 6 }

ospfIntfNbrBadRequests OBJECT-TYPE
    SYNTAX  Counter32
    MAX-ACCESS  read-only
    STATUS  current
    DESCRIPTION
        "The total number of Link State Requests which have been received
         for a link state advertisement not contained in the database for
         this interface."
    ::= { ospfIntfNbrChangeStatsEntry 7 }

ospfIntfNbrBadSequence OBJECT-TYPE
    SYNTAX  Counter32
    MAX-ACCESS  read-only
    STATUS  current
    DESCRIPTION
        "The total number of Database Description packets which have been
         received that either
         a) has an unexpected DD sequence number
         b) Unexpectedly has the init bit set
         c) Has an options field differing from the last Options field
            received in a Database Description packet.
         Any of these conditions indicate that some error has occured during
         adjacency establishment for this interface."
    ::= { ospfIntfNbrChangeStatsEntry 8 }

ospfIntfNbrLoadingDone OBJECT-TYPE
    SYNTAX  Counter32
    MAX-ACCESS  read-only
    STATUS  current
    DESCRIPTION
        "The total number of link state updates received for all
         out-of-date portions of the database for this OSPF interface."
    ::= { ospfIntfNbrChangeStatsEntry 9 }

ospfIntfNbrN1way OBJECT-TYPE
    SYNTAX  Counter32
    MAX-ACCESS  read-only
    STATUS  current
    DESCRIPTION
        "The total number of Hello packets received from neighbours, in
         which this router is not mentioned for this OSPF interface."
    ::= { ospfIntfNbrChangeStatsEntry 10 }

ospfIntfNbrRstAd OBJECT-TYPE
    SYNTAX  Counter32
    MAX-ACCESS  read-only
    STATUS  current
    DESCRIPTION
        "The sum total number of times the Neighbour adjacency has been reset
         on this interface."
    ::= { ospfIntfNbrChangeStatsEntry 11 }

ospfIntfNbrDown OBJECT-TYPE
    SYNTAX  Counter32
    MAX-ACCESS  read-only
    STATUS  current
    DESCRIPTION
        "The total number of Neighbouring routers down (i.e. in the initial
         state of a neighbour conversation.) for this interface."
    ::= { ospfIntfNbrChangeStatsEntry 12 }

ospfIntfNbrN2way OBJECT-TYPE
    SYNTAX  Counter32
    MAX-ACCESS  read-only
    STATUS  current
    DESCRIPTION
        "The total number of Hello packets received from neighbours, in
         which this router is mentioned for this OSPF interface."
    ::= { ospfIntfNbrChangeStatsEntry 13 }

ospfIntfChangeStats OBJECT-TYPE
    SYNTAX SEQUENCE OF OspfIntfChangeStatsEntry
    MAX-ACCESS not-accessible
    STATUS current
    DESCRIPTION
      "The table of OSPF Interface change Statistics."
    ::= { ospfInterface 3 }

ospfIntfChangeStatsEntry OBJECT-TYPE
    SYNTAX OspfIntfChangeStatsEntry
    MAX-ACCESS not-accessible
    STATUS current
    DESCRIPTION
      "OSPF interface Change statistics."
    INDEX { ospfIntfIndex }
    ::= { ospfIntfChangeStats 1 }

OspfIntfChangeStatsEntry ::= SEQUENCE {
    ospfIntfIndex     	       	Integer32,
    ospfIntfHello           	Counter32,
    ospfIntfDown           	Counter32,
    ospfIntfLoop       		Counter32,
    ospfIntfUnloop 		Counter32,
    ospfIntfWaitTimer     	Counter32,
    ospfIntfBackup	        Counter32,
    ospfIntfNbrChange       	Counter32
    }

ospfIntfIndex OBJECT-TYPE
    SYNTAX  Integer32
    MAX-ACCESS  read-only
    STATUS  current
    DESCRIPTION
        "The index of the OSPF Interface for which these statistics apply."
    ::= { ospfIntfChangeStatsEntry 1 }

ospfIntfHello OBJECT-TYPE
    SYNTAX    Counter32
    MAX-ACCESS    read-only
    STATUS    current
    DESCRIPTION
        "The total number of Hello packets sent by this interface."
    ::= { ospfIntfChangeStatsEntry 2 }

ospfIntfDown OBJECT-TYPE
    SYNTAX   Counter32
    MAX-ACCESS   read-only
    STATUS   current
    DESCRIPTION
        "The total number of times the interface was down."
    ::= { ospfIntfChangeStatsEntry 3 }

ospfIntfLoop OBJECT-TYPE
    SYNTAX    Counter32
    MAX-ACCESS    read-only
    STATUS    current
    DESCRIPTION
        "The total number of times the interface was no longer connected to
         the attatched network."
    ::= { ospfIntfChangeStatsEntry 4 }

ospfIntfUnloop OBJECT-TYPE
    SYNTAX   Counter32
    MAX-ACCESS   read-only
    STATUS   current
    DESCRIPTION
        "The total number of times the interface, connected back to
         the attatched network."
    ::= { ospfIntfChangeStatsEntry 5 }

ospfIntfWaitTimer OBJECT-TYPE
    SYNTAX        Counter32
    MAX-ACCESS        read-only
    STATUS        current
    DESCRIPTION
        "The total number of times the Wait Timer has been fired,
         (indicating the end of the waiting period that is required
          before electing a (Backup) Designated Router) for this
          OSPF interface."
    ::= { ospfIntfChangeStatsEntry 6 }

ospfIntfBackup OBJECT-TYPE
    SYNTAX     Counter32
    MAX-ACCESS     read-only
    STATUS     current
    DESCRIPTION
        "The total number of Backup Designated Routers on the attatched
         network for this OSPF interface."
    ::= { ospfIntfChangeStatsEntry 7 }

ospfIntfNbrChange OBJECT-TYPE
    SYNTAX     Counter32
    MAX-ACCESS     read-only
    STATUS     current
    DESCRIPTION
        "The total number of changes in the set of bidirectional neighbours
         associated with the interface for this OSPF interface."
    ::= { ospfIntfChangeStatsEntry 8 }

ospfIntfErrorStats OBJECT-TYPE
    SYNTAX SEQUENCE OF OspfIntfErrorStatsEntry
    MAX-ACCESS not-accessible
    STATUS current
    DESCRIPTION
      "The table of OSPF Interface Error Statistics."
    ::= { ospfInterface 4 }

ospfIntfErrorStatsEntry OBJECT-TYPE
    SYNTAX OspfIntfErrorStatsEntry
    MAX-ACCESS not-accessible
    STATUS current
    DESCRIPTION
      "Error Statistics for an OSPF area."
    INDEX { ospfIntfErrIndex }
    ::= { ospfIntfErrorStats 1 }

OspfIntfErrorStatsEntry ::= SEQUENCE {
    ospfIntfErrIndex     	Integer32,
    ospfIntfErrAuthFailure      Counter32,
    ospfIntfErrNetmaskMismatch  Counter32,
    ospfIntfErrHelloMismatch    Counter32,
    ospfIntfErrDeadMismatch     Counter32,
    ospfIntfErrOptionsMismatch  Counter32,
    ospfIntfErrUnknownNbr       Counter32
    }

ospfIntfErrIndex OBJECT-TYPE
    SYNTAX    Integer32
    MAX-ACCESS    read-only
    STATUS    current
    DESCRIPTION
        "The index of the OSPF Intf for which these statistics apply."
    ::= { ospfIntfErrorStatsEntry 1 }

ospfIntfErrAuthFailure OBJECT-TYPE
    SYNTAX    Counter32
    MAX-ACCESS    read-only
    STATUS    current
    DESCRIPTION
        "The total number of packets received with a wrong password in
         this area."
    ::= { ospfIntfErrorStatsEntry 2 }

ospfIntfErrNetmaskMismatch OBJECT-TYPE
    SYNTAX    Counter32
    MAX-ACCESS    read-only
    STATUS    current
    DESCRIPTION
        "The total number of packets received with a wrong netmask in
         this area."
    ::= { ospfIntfErrorStatsEntry 3 }

ospfIntfErrHelloMismatch OBJECT-TYPE
    SYNTAX    Counter32
    MAX-ACCESS    read-only
    STATUS    current
    DESCRIPTION
        "The total number of packets received with a different hello interval
         in this area."
    ::= { ospfIntfErrorStatsEntry 4 }

ospfIntfErrDeadMismatch OBJECT-TYPE
    SYNTAX    Counter32
    MAX-ACCESS    read-only
    STATUS    current
    DESCRIPTION
        "The total number of packets received with a different dead interval
         in this area."
    ::= { ospfIntfErrorStatsEntry 5 }

ospfIntfErrOptionsMismatch OBJECT-TYPE
    SYNTAX    Counter32
    MAX-ACCESS    read-only
    STATUS    current
    DESCRIPTION
        "The total number of packets received with a different options
         in this area."
    ::= { ospfIntfErrorStatsEntry 6 }

ospfIntfErrUnknownNbr OBJECT-TYPE
    SYNTAX    Counter32
    MAX-ACCESS    read-only
    STATUS    current
    DESCRIPTION
        "The total number of packets received from an unknown neighbour
         in this area."
    ::= { ospfIntfErrorStatsEntry 7 }

-- Ospf General Statistics contains the cumulative stats for all
-- areas / interfaces
ospfCumRxPkts OBJECT-TYPE
    SYNTAX  Counter32
    MAX-ACCESS  read-only
    STATUS  current
    DESCRIPTION
        "The sum total of all OSPF packets received on all OSPF areas
         and interfaces."
    ::= { ospfCumRxTxStats 1 }

ospfCumTxPkts OBJECT-TYPE
    SYNTAX  Counter32
    MAX-ACCESS  read-only
    STATUS  current
    DESCRIPTION
        "The sum total of all OSPF packets transmitted on all OSPF areas
         and interfaces."
    ::= { ospfCumRxTxStats 2 }

ospfCumRxHello OBJECT-TYPE
    SYNTAX  Counter32
    MAX-ACCESS  read-only
    STATUS  current
    DESCRIPTION
        "The sum total of all Hello packets received on all OSPF areas
         and interfaces."
    ::= { ospfCumRxTxStats 3 }

ospfCumTxHello OBJECT-TYPE
    SYNTAX  Counter32
    MAX-ACCESS  read-only
    STATUS  current
    DESCRIPTION
        "The sum total of all Hello packets transmitted on all OSPF areas
         and interfaces."
    ::= { ospfCumRxTxStats 4 }

ospfCumRxDatabase OBJECT-TYPE
    SYNTAX  Counter32
    MAX-ACCESS  read-only
    STATUS  current
    DESCRIPTION
        "The sum total of all Database Description packets received on
         all OSPF areas and interfaces."
    ::= { ospfCumRxTxStats 5 }

ospfCumTxDatabase OBJECT-TYPE
    SYNTAX  Counter32
    MAX-ACCESS  read-only
    STATUS  current
    DESCRIPTION
        "The sum total of all Database Description packets transmitted on
         all OSPF areas and interfaces."
    ::= { ospfCumRxTxStats 6 }

ospfCumRxlsReqs OBJECT-TYPE
    SYNTAX  Counter32
    MAX-ACCESS  read-only
    STATUS  current
    DESCRIPTION
        "The sum total of all Link State Request packets received on
         all OSPF areas and interfaces."
    ::= { ospfCumRxTxStats 7 }

ospfCumTxlsReqs OBJECT-TYPE
    SYNTAX  Counter32
    MAX-ACCESS  read-only
    STATUS  current
    DESCRIPTION
        "The sum total of all Link State Request packets transmitted on
         all OSPF areas and interfaces."
    ::= { ospfCumRxTxStats 8 }

ospfCumRxlsAcks OBJECT-TYPE
    SYNTAX  Counter32
    MAX-ACCESS  read-only
    STATUS  current
    DESCRIPTION
        "The sum total of all Link State Acknowledgement packets received
         on all OSPF areas and interfaces."
    ::= { ospfCumRxTxStats 9 }

ospfCumTxlsAcks OBJECT-TYPE
    SYNTAX  Counter32
    MAX-ACCESS  read-only
    STATUS  current
    DESCRIPTION
        "The sum total of all Link State Acknowledgement packets transmitted
         on all OSPF areas and interfaces."
    ::= { ospfCumRxTxStats 10 }

ospfCumRxlsUpdates OBJECT-TYPE
    SYNTAX  Counter32
    MAX-ACCESS  read-only
    STATUS  current
    DESCRIPTION
        "The sum total of all Link State Update packets received
         on all OSPF areas and interfaces."
    ::= { ospfCumRxTxStats 11 }

ospfCumTxlsUpdates OBJECT-TYPE
    SYNTAX  Counter32
    MAX-ACCESS  read-only
    STATUS  current
    DESCRIPTION
        "The sum total of all Link State Update packets transmitted
         on all OSPF areas and interfaces."
    ::= { ospfCumRxTxStats 12 }

ospfCumNbrhello OBJECT-TYPE
    SYNTAX  Counter32
    MAX-ACCESS  read-only
    STATUS  current
    DESCRIPTION
        "The sum total of all Hello packets received from neighbours
         on all OSPF areas and interfaces."
    ::= { ospfCumNbrChangeStats 1 }

ospfCumNbrStart OBJECT-TYPE
    SYNTAX  Counter32
    MAX-ACCESS  read-only
    STATUS  current
    DESCRIPTION
        "The sum total number of neighbours in this state (i.e. an indication
         that  Hello packets should now be sent to the neighbour at intervals
         of HelloInterval seconds.) across all OSPF areas and interfaces."
    ::= { ospfCumNbrChangeStats 2 }

ospfCumNbrAdjointOk OBJECT-TYPE
    SYNTAX  Counter32
    MAX-ACCESS  read-only
    STATUS  current
    DESCRIPTION
        "The sum total number of decisions to be made (again) as to whether
         an adjacency should be established/maintained with the neighbour
         across all OSPF areas and interfaces."
    ::= { ospfCumNbrChangeStats 3 }

ospfCumNbrNegotiationDone OBJECT-TYPE
    SYNTAX  Counter32
    MAX-ACCESS  read-only
    STATUS  current
    DESCRIPTION
        "The sum total number of neighbours in this state wherein the
         Master/slave relationship has been negotiated, and sequence
         numbers have been exchanged, across all OSPF areas and
         interfaces."
    ::= { ospfCumNbrChangeStats 4 }

ospfCumNbrExchangeDone OBJECT-TYPE
    SYNTAX  Counter32
    MAX-ACCESS  read-only
    STATUS  current
    DESCRIPTION
        "The sum total number of neighbours in this state (i.e. in an
         adjacency's final state) having transimitted a full sequence
         of Database Description packets, across all OSPF areas
         and interfaces."
    ::= { ospfCumNbrChangeStats 5 }

ospfCumNbrBadRequests OBJECT-TYPE
    SYNTAX  Counter32
    MAX-ACCESS  read-only
    STATUS  current
    DESCRIPTION
        "The sum total number of Link State Requests which have been received
         for a link state advertisement not contained in the database across
         all interfaces and OSPF areas."
    ::= { ospfCumNbrChangeStats 6 }

ospfCumNbrBadSequence OBJECT-TYPE
    SYNTAX  Counter32
    MAX-ACCESS  read-only
    STATUS  current
    DESCRIPTION
        "The sum total number of Database Description packets which have been
         received that either
         a) has an unexpected DD sequence number
         b) Unexpectedly has the init bit set
         c) Has an options field differing from the last Options field
            received in a Database Description packet.
         Any of these conditions indicate that some error has occured during
         adjacency establishment for all OSPF areas and interfaces."
    ::= { ospfCumNbrChangeStats 7 }

ospfCumNbrLoadingDone OBJECT-TYPE
    SYNTAX  Counter32
    MAX-ACCESS  read-only
    STATUS  current
    DESCRIPTION
        "The sum total number of link state updates received for all
         out-of-date portions of the database across all OSPF areas
         and interfaces."
    ::= { ospfCumNbrChangeStats 8 }

ospfCumNbrN1way OBJECT-TYPE
    SYNTAX  Counter32
    MAX-ACCESS  read-only
    STATUS  current
    DESCRIPTION
        "The sum total number of Hello packets received from neighbours, in
         which this router is not mentioned across all OSPF interfaces
         and areas."
    ::= { ospfCumNbrChangeStats 9 }

ospfCumNbrRstAd OBJECT-TYPE
    SYNTAX  Counter32
    MAX-ACCESS  read-only
    STATUS  current
    DESCRIPTION
        "The sum total number of times the Neighbour adjacency has been reset
         across all OPSF areas and interfaces."
    ::= { ospfCumNbrChangeStats 10 }

ospfCumNbrDown OBJECT-TYPE
    SYNTAX  Counter32
    MAX-ACCESS  read-only
    STATUS  current
    DESCRIPTION
        "The total number of Neighbouring routers down (i.e. in the initial
         state of a neighbour conversation.) across all OSPF areas and
         interfaces."
    ::= { ospfCumNbrChangeStats 11 }

ospfCumNbrN2way OBJECT-TYPE
    SYNTAX  Counter32
    MAX-ACCESS  read-only
    STATUS  current
    DESCRIPTION
        "The sum total number of Hello packets received from neighbours, in
         which this router is mentioned across all OSPF interfaces
         and areas."
    ::= { ospfCumNbrChangeStats 12 }

ospfCumIntfHello OBJECT-TYPE
    SYNTAX    Counter32
    MAX-ACCESS    read-only
    STATUS    current
    DESCRIPTION
        "The sum total number of Hello packets sent on all interfaces
         and areas"
    ::= { ospfCumIntfChangeStats 1 }

ospfCumIntfDown OBJECT-TYPE
    SYNTAX   Counter32
    MAX-ACCESS   read-only
    STATUS   current
    DESCRIPTION
        "The sum total number of interfaces down in all OSPF areas."
    ::= { ospfCumIntfChangeStats 2 }

ospfCumIntfLoop OBJECT-TYPE
    SYNTAX    Counter32
    MAX-ACCESS    read-only
    STATUS    current
    DESCRIPTION
        "The sum total of interfaces no longer connected to
         the attatched network across all OSPF areas and interfaces."
    ::= { ospfCumIntfChangeStats 3 }

ospfCumIntfUnloop OBJECT-TYPE
    SYNTAX   Counter32
    MAX-ACCESS   read-only
    STATUS   current
    DESCRIPTION
        "The sum total number of interfaces, connected to
         the attatched network in all OSPF areas."
    ::= { ospfCumIntfChangeStats 4 }

ospfCumIntfWaitTimer OBJECT-TYPE
    SYNTAX        Counter32
    MAX-ACCESS        read-only
    STATUS        current
    DESCRIPTION
        "The sum total number of times the Wait Timer has been fired,
         (indicating the end of the waiting period that is required
          before electing a (Backup) Designated Router) across all
          OSPF areas and interfaces."
    ::= { ospfCumIntfChangeStats 5 }

ospfCumIntfBackup OBJECT-TYPE
    SYNTAX     Counter32
    MAX-ACCESS     read-only
    STATUS     current
    DESCRIPTION
        "The sum total number of Backup Designated Routers on the attatched
         network for all OSPF areas and interfaces."
    ::= { ospfCumIntfChangeStats 6 }

ospfCumIntfNbrChange OBJECT-TYPE
    SYNTAX     Counter32
    MAX-ACCESS     read-only
    STATUS     current
    DESCRIPTION
        "The sum total number of changes in the set of bidirectional
         neighbours associated with any interface across all OSPF areas."
    ::= { ospfCumIntfChangeStats 7 }

ospfTmrsKckOffHello OBJECT-TYPE
    SYNTAX    Counter32
    MAX-ACCESS    read-only
    STATUS    current
    DESCRIPTION
        "The sum total number of times the Hello timer has been fired
         (which triggers the send of a Hello packet) across all OPSF
         areas and interfaces."
    ::= { ospfTimersKickOffStats 1 }

ospfTmrsKckOffRetransmit OBJECT-TYPE
    SYNTAX   Counter32
    MAX-ACCESS   read-only
    STATUS   current
    DESCRIPTION
        "The sum total number of times the Retransmit timer has been
         fired across all OPSF areas and interfaces."
    ::= { ospfTimersKickOffStats 2 }

ospfTmrsKckOffLsaLock OBJECT-TYPE
    SYNTAX    Counter32
    MAX-ACCESS    read-only
    STATUS    current
    DESCRIPTION
        "The sum total number of times the Lsa Lock timer has been
         fired across all OSPF areas and interfaces."
    ::= { ospfTimersKickOffStats 3 }

ospfTmrsKckOffLsaAck OBJECT-TYPE
    SYNTAX   Counter32
    MAX-ACCESS   read-only
    STATUS   current
    DESCRIPTION
        "The sum total number of times the Lsa Ack timer has been
         fired across all ospf areas and interfaces."
    ::= { ospfTimersKickOffStats 4 }

ospfTmrsKckOffDbage OBJECT-TYPE
    SYNTAX        Counter32
    MAX-ACCESS        read-only
    STATUS        current
    DESCRIPTION
        "The total number of times the Dbage has been fired."
    ::= { ospfTimersKickOffStats 5 }

ospfTmrsKckOffSummary OBJECT-TYPE
    SYNTAX     Counter32
    MAX-ACCESS     read-only
    STATUS     current
    DESCRIPTION
        "The total number of times the Summary timer has been fired."
    ::= { ospfTimersKickOffStats 6 }

ospfTmrsKckOffAseExport OBJECT-TYPE
    SYNTAX     Counter32
    MAX-ACCESS     read-only
    STATUS     current
    DESCRIPTION
        "The total number of times the ASE Export timer has been fired."
    ::= { ospfTimersKickOffStats 7 }




ip6InReceives OBJECT-TYPE
    SYNTAX  Counter32
    MAX-ACCESS  read-only
    STATUS  current
    DESCRIPTION
        "The total number of input datagrams received from
         interfaces, including those received in error."
    ::= { ip6Stats 1 }

ip6ForwDatagrams OBJECT-TYPE
    SYNTAX  Counter32
    MAX-ACCESS  read-only
    STATUS  current
    DESCRIPTION
        "The number of input datagrams for which this entity was not
         their final IP destination, as a result of which an attempt
         was made to find a route to forward them to that final
         destination."
    ::= { ip6Stats 2 }

ip6InDelivers OBJECT-TYPE
    SYNTAX  Counter32
    MAX-ACCESS  read-only
    STATUS  current
    DESCRIPTION
        "The total number of input datagrams successfully
         delivered to IP user-protocols (including ICMP)."
    ::= { ip6Stats 3 }

ip6InDiscards OBJECT-TYPE
    SYNTAX  Counter32
    MAX-ACCESS  read-only
    STATUS  current
    DESCRIPTION
        "The number of input IP datagrams for which no problems were
         encountered to prevent their continued processing, but which were
         discarded (e.g., for lack of buffer space).  Note that this counter
         does not include any datagrams discarded while awaiting re-assembly."
         ::= { ip6Stats 4 }

ip6InUnknownProtos OBJECT-TYPE
    SYNTAX  Counter32
    MAX-ACCESS  read-only
    STATUS  current
    DESCRIPTION
        "The number of locally-addressed datagrams received successfully
         but discarded because of an unknown or unsupported protocol."
    ::= { ip6Stats 5 }

ip6InAddrErrors OBJECT-TYPE
    SYNTAX  Counter32
    MAX-ACCESS  read-only
    STATUS  current
    DESCRIPTION
        "The number of input datagrams discarded because the IP address
         in their IP header's destination field was not a valid address
         to be received at this entity."
    ::= { ip6Stats 6 }

ip6OutRequests OBJECT-TYPE
    SYNTAX  Counter32
    MAX-ACCESS  read-only
    STATUS  current
    DESCRIPTION
        "The total number of IP datagrams which local IP
         user-protocols (including ICMP) supplied to IP in
         requests for transmission.  Note that this counter does not
         include any datagrams counted in ipForwDatagrams."
    ::= { ip6Stats 7 }

ip6OutNoRoutes OBJECT-TYPE
    SYNTAX  Counter32
    MAX-ACCESS  read-only
    STATUS  current
    DESCRIPTION
        "The number of IP datagrams discarded because no route
        could be found to transmit them to their destination.
        Note that this Counter32 includes any packets counted in
        ipForwDatagrams which meet this`no-route' criterion.
        Note that this includes any datagrams which a host cannot
        route because all of its default gateways are down."
    ::= { ip6Stats 8 }

ip6ReasmOKs OBJECT-TYPE
    SYNTAX  Counter32
    MAX-ACCESS  read-only
    STATUS  current
    DESCRIPTION
        "The number of IP datagrams successfully re-assembled."
    ::= { ip6Stats 9 }

ip6ReasmFails OBJECT-TYPE
    SYNTAX  Counter32
    MAX-ACCESS  read-only
    STATUS  current
    DESCRIPTION
        "The number of failures detected by the IP re-assembly."
    ::= { ip6Stats 10 }

ip6icmpInMsgs OBJECT-TYPE
    SYNTAX  Counter32
    MAX-ACCESS  read-only
    STATUS  current
    DESCRIPTION
        "The total number of ICMP messages received.
         Note that this Counter32 includes all those counted by
         icmpInErrors."
    ::= { ip6Stats 11 }

ip6icmpOutMsgs OBJECT-TYPE
    SYNTAX  Counter32
    MAX-ACCESS  read-only
    STATUS  current
    DESCRIPTION
        "The total number of ICMP messages attempted to send.  Note that
         this Counter32 includes all those counted by icmp6OutErrors."
    ::= { ip6Stats 12}

ip6icmpInErrors OBJECT-TYPE
    SYNTAX  Counter32
    MAX-ACCESS  read-only
    STATUS  current
    DESCRIPTION
        "The number of ICMP messages received but determined as having
         ICMP-specific errors (bad ICMP checksums, bad length, etc.)."
    ::= { ip6Stats 13 }

ip6icmpOutErrors OBJECT-TYPE
    SYNTAX  Counter32
    MAX-ACCESS  read-only
    STATUS  current
    DESCRIPTION
        "The number of ICMP messages did not send due to problems
         discovered within ICMP such as a lack of buffers."
    ::= { ip6Stats 14}

icmp6StatsTable  OBJECT-TYPE
    SYNTAX SEQUENCE OF Icmp6StatsEntry
    MAX-ACCESS not-accessible
    STATUS current
    DESCRIPTION
        "Statistics for ICMP6."
    ::= { icmp6Stats 1 }

icmp6StatsEntry  OBJECT-TYPE
    SYNTAX  Icmp6StatsEntry
    MAX-ACCESS not-accessible
    STATUS current
    DESCRIPTION
      "Statistics for IGMP Snooping."
    INDEX { icmp6StatsIndx}
    ::= { icmp6StatsTable 1 }

Icmp6StatsEntry ::= SEQUENCE {
    icmp6StatsIndx         Integer32,
    icmp6IntfIndex         Integer32,
    icmp6InMsgs            Counter32,
    icmp6InErrors          Counter32,
    icmp6InEchos           Counter32,
    icmp6InEchoReps        Counter32,
    icmp6InNSs             Counter32,
    icmp6InNAs             Counter32,
    icmp6InRSs             Counter32,
    icmp6InRAs             Counter32,
    icmp6InDestUnreachs    Counter32,
    icmp6InTimeExcds       Counter32,
    icmp6InTooBigs         Counter32,
    icmp6InParmProbs       Counter32,
    icmp6InRedirects       Counter32,
    icmp6OutMsgs           Counter32,
    icmp6OutErrors         Counter32,
    icmp6OutEchos          Counter32,
    icmp6OutEchoReps       Counter32,
    icmp6OutNSs            Counter32,
    icmp6OutNAs            Counter32,
    icmp6OutRSs            Counter32,
    icmp6OutRAs            Counter32,
    icmp6OutRedirects      Counter32
    }

icmp6StatsIndx   OBJECT-TYPE
    SYNTAX    Integer32
    MAX-ACCESS    read-only
    STATUS    current
    DESCRIPTION
        "The index of this statistics table."
    ::= { icmp6StatsEntry 1 }

icmp6IntfIndex   OBJECT-TYPE
    SYNTAX    Integer32
    MAX-ACCESS    read-only
    STATUS    current
    DESCRIPTION
        "IP interface index in interface configuration table."
    ::= { icmp6StatsEntry 2 }

icmp6InMsgs OBJECT-TYPE
    SYNTAX  Counter32
    MAX-ACCESS  read-only
    STATUS  current
    DESCRIPTION
        "The total number of ICMP messages received.  Note that this
         Counter32 includes all those counted by icmpInErrors."
    ::= { icmp6StatsEntry 3 }

icmp6InErrors OBJECT-TYPE
    SYNTAX  Counter32
    MAX-ACCESS  read-only
    STATUS  current
    DESCRIPTION
        "The number of ICMP messages received but determined as having
         ICMP-specific errors (bad ICMP checksums, bad length, etc.)."
    ::= { icmp6StatsEntry 4 }

icmp6InEchos OBJECT-TYPE
    SYNTAX  Counter32
    MAX-ACCESS  read-only
    STATUS  current
    DESCRIPTION
        "The number of ICMP Echo request messages received."
    ::= { icmp6StatsEntry 5 }

icmp6InEchoReps OBJECT-TYPE
    SYNTAX  Counter32
    MAX-ACCESS  read-only
    STATUS  current
    DESCRIPTION
        "The number of ICMP Echo Reply messages received."
    ::= { icmp6StatsEntry 6 }

icmp6InNSs OBJECT-TYPE
    SYNTAX  Counter32
    MAX-ACCESS  read-only
    STATUS  current
    DESCRIPTION
        "The number of neighbour solicitations received."
    ::= { icmp6StatsEntry 7 }

icmp6InNAs OBJECT-TYPE
    SYNTAX  Counter32
    MAX-ACCESS  read-only
    STATUS  current
    DESCRIPTION
        "The number of neighbour advertisements received."
    ::= { icmp6StatsEntry 8 }

icmp6InRSs OBJECT-TYPE
    SYNTAX  Counter32
    MAX-ACCESS  read-only
    STATUS  current
    DESCRIPTION
        "The number of router solicitations received."
    ::= { icmp6StatsEntry 9 }

icmp6InRAs OBJECT-TYPE
    SYNTAX  Counter32
    MAX-ACCESS  read-only
    STATUS  current
    DESCRIPTION
        "The number of router advertisements received."
    ::= { icmp6StatsEntry 10 }

icmp6InDestUnreachs OBJECT-TYPE
    SYNTAX  Counter32
    MAX-ACCESS  read-only
    STATUS  current
    DESCRIPTION
        "The number of ICMP Destination Unreachable messages received."
    ::= { icmp6StatsEntry 11 }

icmp6InTimeExcds OBJECT-TYPE
    SYNTAX  Counter32
    MAX-ACCESS  read-only
    STATUS  current
    DESCRIPTION
        "The number of ICMP Time Exceeded messages received."
    ::= { icmp6StatsEntry 12 }

icmp6InTooBigs  OBJECT-TYPE
    SYNTAX  Counter32
    MAX-ACCESS  read-only
    STATUS  current
    DESCRIPTION
        "The number of ICMP too big messages received."
    ::= { icmp6StatsEntry 13 }

icmp6InParmProbs OBJECT-TYPE
    SYNTAX  Counter32
    MAX-ACCESS  read-only
    STATUS  current
    DESCRIPTION
        "The number of ICMP Parameter Problem messages received."
    ::= { icmp6StatsEntry 14 }

icmp6InRedirects OBJECT-TYPE
    SYNTAX  Counter32
    MAX-ACCESS  read-only
    STATUS  current
    DESCRIPTION
        "The number of ICMP Redirect messages received."
    ::= { icmp6StatsEntry 15 }

icmp6OutMsgs OBJECT-TYPE
    SYNTAX  Counter32
    MAX-ACCESS  read-only
    STATUS  current
    DESCRIPTION
        "The total number of ICMP messages which this entity
         attempted to send.  Note that this Counter32 includes
         all those counted by icmp6OutErrors."
    ::= { icmp6StatsEntry 16 }

icmp6OutErrors OBJECT-TYPE
    SYNTAX  Counter32
    MAX-ACCESS  read-only
    STATUS  current
    DESCRIPTION
        "The number of ICMP messages which this entity did not
         send due to problems discovered within ICMP
         such as a lack of buffers."
    ::= { icmp6StatsEntry 17 }

icmp6OutEchos OBJECT-TYPE
    SYNTAX  Counter32
    MAX-ACCESS  read-only
    STATUS  current
    DESCRIPTION
        "The number of ICMP Echo request messages sent."
    ::= { icmp6StatsEntry 18 }

icmp6OutEchoReps OBJECT-TYPE
    SYNTAX  Counter32
    MAX-ACCESS  read-only
    STATUS  current
    DESCRIPTION
        "The number of ICMP Echo Reply messages sent."
    ::= { icmp6StatsEntry 19 }

icmp6OutNSs OBJECT-TYPE
    SYNTAX  Counter32
    MAX-ACCESS  read-only
    STATUS  current
    DESCRIPTION
        "The number of neighbour solicitations sent."
    ::= { icmp6StatsEntry 20 }

icmp6OutNAs OBJECT-TYPE
    SYNTAX  Counter32
    MAX-ACCESS  read-only
    STATUS  current
    DESCRIPTION
        "The number of neighbour advertisements sent."
    ::= { icmp6StatsEntry 21 }

icmp6OutRSs OBJECT-TYPE
    SYNTAX  Counter32
    MAX-ACCESS  read-only
    STATUS  current
    DESCRIPTION
        "The number of router solicitations sent."
    ::= { icmp6StatsEntry 22 }

icmp6OutRAs OBJECT-TYPE
    SYNTAX  Counter32
    MAX-ACCESS  read-only
    STATUS  current
    DESCRIPTION
        "The number of router advertisements sent."
    ::= { icmp6StatsEntry 23 }

icmp6OutRedirects OBJECT-TYPE
    SYNTAX  Counter32
    MAX-ACCESS  read-only
    STATUS  current
    DESCRIPTION
        "The number of ICMP Redirect messages sent.  For a host, this
         object will always be zero, since hosts do not send redirects."
    ::= { icmp6StatsEntry 24 }

ip6GwStatsTable OBJECT-TYPE
    SYNTAX SEQUENCE OF Ip6GwStatsEntry
    MAX-ACCESS not-accessible
    STATUS current
    DESCRIPTION
        "Statistics for IP6 Gateway."
    ::= { ip6gwStats 1 }

ip6GwStatsEntry OBJECT-TYPE
    SYNTAX Ip6GwStatsEntry
    MAX-ACCESS not-accessible
    STATUS current
    DESCRIPTION
      "Statistics for IP6 Gateway."
    INDEX { ip6GwStatsIndex}
    ::= { ip6GwStatsTable 1 }

Ip6GwStatsEntry ::= SEQUENCE {
    ip6GwStatsIndex       Integer32,
    ip6GwIndex            Integer32,
    ip6GwEchoreq          Counter32,
    ip6GwEchoresp         Counter32,
    ip6GwFails            Counter32,
    ip6GwMaster           Integer32,
    ip6IfIndex            Integer32,
    ip6GwRetry            Counter32
}

ip6GwStatsIndex  OBJECT-TYPE
    SYNTAX Integer32
    MAX-ACCESS  read-only
    STATUS  current
    DESCRIPTION
        "The index of Gw6 statistics."
    ::= { ip6GwStatsEntry 1}

ip6GwIndex  OBJECT-TYPE
    SYNTAX Integer32
    MAX-ACCESS  read-only
    STATUS  current
    DESCRIPTION
        "Gateway index in gateway configuration table."
    ::= { ip6GwStatsEntry 2}

ip6GwEchoreq  OBJECT-TYPE
    SYNTAX    Counter32
    MAX-ACCESS    read-only
    STATUS    current
    DESCRIPTION
        "The number of GW Echo request messages ."
    ::= { ip6GwStatsEntry 3 }

ip6GwEchoresp  OBJECT-TYPE
    SYNTAX   Counter32
    MAX-ACCESS    read-only
    STATUS    current
    DESCRIPTION
        "The number of GW Echo response messages ."
    ::= { ip6GwStatsEntry 4 }

ip6GwFails  OBJECT-TYPE
    SYNTAX   Counter32
    MAX-ACCESS    read-only
    STATUS    current
    DESCRIPTION
        "The number of GWs fails."
    ::= { ip6GwStatsEntry 5 }

ip6GwMaster  OBJECT-TYPE
    SYNTAX  Integer32
    MAX-ACCESS    read-only
    STATUS    current
    DESCRIPTION
        "The master gateway."
    ::= { ip6GwStatsEntry 6 }

ip6IfIndex  OBJECT-TYPE
    SYNTAX  Integer32
    MAX-ACCESS    read-only
    STATUS    current
    DESCRIPTION
        "The IP6 interface."
    ::= { ip6GwStatsEntry 7 }

ip6GwRetry OBJECT-TYPE
    SYNTAX Counter32
    MAX-ACCESS    read-only
    STATUS    current
    DESCRIPTION
        "The number of retries."
    ::= { ip6GwStatsEntry 8 }


-- Information - Run-time IP Route Table


ipIntfInfoTable OBJECT-TYPE
    SYNTAX  SEQUENCE OF IntfInfoEntry
    MAX-ACCESS not-accessible
    STATUS current
    DESCRIPTION
        "The table of IP interface information."
    ::= {ipIntfInfo 1 }

intfInfoEntry OBJECT-TYPE
    SYNTAX  IntfInfoEntry
    MAX-ACCESS not-accessible
    STATUS  current
    DESCRIPTION
        "A row in IP interface information table."
    INDEX   { intfInfoIndex }
    ::= { ipIntfInfoTable 1 }

IntfInfoEntry ::= SEQUENCE {
    intfInfoIndex        Integer32,
    intfInfoIpver         INTEGER,
    intfInfoAddr          DisplayString,
    intfInfoNetMask       DisplayString,
    intfInfoBcastAddr     DisplayString,
    intfInfoVlan          Integer32,
    intfInfoLinkLocalAddr DisplayString,
    intfInfoStatus        INTEGER
    }

intfInfoIndex OBJECT-TYPE
    SYNTAX  Integer32
    MAX-ACCESS  read-only
    STATUS  current
    DESCRIPTION
	"The interface number for which the information is related."
    ::= { intfInfoEntry 1}


intfInfoIpver  OBJECT-TYPE
    SYNTAX   INTEGER {
        ipv4(1),
        ipv6(2)
    }
    MAX-ACCESS  read-only
    STATUS  current
    DESCRIPTION
        "The type of IP address."
    ::= { intfInfoEntry 2 }


intfInfoAddr  OBJECT-TYPE
    SYNTAX   DisplayString
    MAX-ACCESS  read-only
    STATUS  current
    DESCRIPTION
	"The IP address of the interface."
    ::= { intfInfoEntry 3 }

intfInfoNetMask OBJECT-TYPE
    SYNTAX   DisplayString
    MAX-ACCESS  read-only
    STATUS  current
    DESCRIPTION
        "The subnet mask of the interface."
    ::= { intfInfoEntry 4 }

intfInfoBcastAddr OBJECT-TYPE
    SYNTAX   DisplayString
    MAX-ACCESS  read-only
    STATUS  current
    DESCRIPTION
        "The broadcast address of the interface."
    ::= { intfInfoEntry 5 }

intfInfoVlan OBJECT-TYPE
    SYNTAX  Integer32
    MAX-ACCESS  read-only
    STATUS  current
    DESCRIPTION
        "The VLAN number for this interface."
    ::= { intfInfoEntry 6 }

intfInfoStatus OBJECT-TYPE
    SYNTAX  INTEGER {
	up(1),
	down(2),
        disabled(3)
    }
    MAX-ACCESS  read-only
    STATUS  current
    DESCRIPTION
	"The status of the interface."
    ::= { intfInfoEntry 7 }


intfInfoLinkLocalAddr OBJECT-TYPE
    SYNTAX   DisplayString
    MAX-ACCESS  read-only
    STATUS  current
    DESCRIPTION
        "The site local address of the interface."
    ::= { intfInfoEntry 8 }


ipRouteInfoTable OBJECT-TYPE
    SYNTAX  SEQUENCE OF IpRouteInfoEntry
    MAX-ACCESS  not-accessible
    STATUS  current
    DESCRIPTION
        "The table of run-time IP routes."
    ::= { ipRoutingInfo 1 }

ipRouteInfoEntry OBJECT-TYPE
    SYNTAX  IpRouteInfoEntry
    MAX-ACCESS  not-accessible
    STATUS  current
    DESCRIPTION
        "A row in the run-time IP route table"
    INDEX   { ipRouteInfoIndx }
    ::= { ipRouteInfoTable 1 }

IpRouteInfoEntry ::= SEQUENCE {
    ipRouteInfoIndx	        Integer32,
    ipRouteInfoDestIp           IpAddress,
    ipRouteInfoMask             IpAddress,
    ipRouteInfoGateway          IpAddress,
    ipRouteInfoTag       	INTEGER,
    ipRouteInfoType       	INTEGER,
    ipRouteInfoInterface        Integer32,
    ipRouteInfoGateway1         IpAddress,
    ipRouteInfoGateway2         IpAddress,
    ipRouteInfoMetric           Integer32
    }

ipRouteInfoIndx OBJECT-TYPE
    SYNTAX  Integer32
    MAX-ACCESS  read-only
    STATUS  current
    DESCRIPTION
        "The index of this route table."
    ::= { ipRouteInfoEntry 1 }

ipRouteInfoDestIp OBJECT-TYPE
    SYNTAX  IpAddress
    MAX-ACCESS  read-only
    STATUS  current
    DESCRIPTION
        "The destination IP address of this route."
    ::= { ipRouteInfoEntry 2 }

ipRouteInfoMask OBJECT-TYPE
    SYNTAX  IpAddress
    MAX-ACCESS  read-only
    STATUS  current
    DESCRIPTION
        "The destination IP mask of this route."
    ::= { ipRouteInfoEntry 3 }

ipRouteInfoGateway OBJECT-TYPE
    SYNTAX  IpAddress
    MAX-ACCESS  read-only
    STATUS  current
    DESCRIPTION
        "The next-hop router address for this route."
    ::= { ipRouteInfoEntry 4 }

ipRouteInfoTag OBJECT-TYPE
    SYNTAX  INTEGER {
	fixed(1),
  	static(2),
	addr(3),
	rip(4),
	broadcast(5),
	martian(6),
	multicast(7),
        vip(8),
        bgp(9),
        ospf(10),
        none(11)
	}
    MAX-ACCESS  read-only
    STATUS  current
    DESCRIPTION
        "The tag-type for this route."
    ::= { ipRouteInfoEntry 5 }

ipRouteInfoType OBJECT-TYPE
    SYNTAX  INTEGER {
	indirect(1),
	direct(2),
	local(3),
	broadcast(4),
	martian(5),
	multicast(6),
	other(7)
	}
    MAX-ACCESS  read-only
    STATUS  current
    DESCRIPTION
        "The type of the route."
    ::= { ipRouteInfoEntry 6 }

ipRouteInfoInterface OBJECT-TYPE
    SYNTAX  Integer32
    MAX-ACCESS  read-only
    STATUS  current
    DESCRIPTION
        "The interface number for which the destination	address is applicable."
    ::= { ipRouteInfoEntry 7 }

ipRouteInfoGateway1 OBJECT-TYPE
    SYNTAX  IpAddress
    MAX-ACCESS  read-only
    STATUS  current
    DESCRIPTION
        "The next-hop router address for this route."
    ::= { ipRouteInfoEntry 8 }

ipRouteInfoGateway2 OBJECT-TYPE
    SYNTAX  IpAddress
    MAX-ACCESS  read-only
    STATUS  current
    DESCRIPTION
        "The next-hop router address for this route."
    ::= { ipRouteInfoEntry 9 }

ipRouteInfoMetric OBJECT-TYPE
    SYNTAX Integer32
    MAX-ACCESS  read-only
    STATUS  current
    DESCRIPTION
        "The Metric for this route."
    ::= { ipRouteInfoEntry 10 }

routeTableClear OBJECT-TYPE
    SYNTAX  INTEGER {
        ok(1),
        clear(2)
        }
    MAX-ACCESS  read-write
    STATUS  current
    DESCRIPTION
        "Setting this value to clear(2) clears the route table."
    ::= { ipRoutingInfo 2 }

-- Run Time ARP Table

arpInfoTable OBJECT-TYPE
    SYNTAX  SEQUENCE OF AgArpInfoEntry
    MAX-ACCESS  not-accessible
    STATUS  current
    DESCRIPTION
        "The table of ARP entries."
    ::= { arpInfo 1 }

arpInfoEntry OBJECT-TYPE
    SYNTAX  AgArpInfoEntry
    MAX-ACCESS  not-accessible
    STATUS  current
    DESCRIPTION
        "A row in the ARP table"
    INDEX   { arpInfoDestIp }
    ::= { arpInfoTable 1 }

AgArpInfoEntry ::= SEQUENCE {
    arpInfoDestIp         IpAddress,
    arpInfoMacAddr        PhysAddress,
    arpInfoVLAN        	  Integer32,
    arpInfoSrcPort        Integer32,
    arpInfoRefPorts       Integer32,
    arpInfoFlag           INTEGER
    }

arpInfoDestIp OBJECT-TYPE
    SYNTAX  IpAddress
    MAX-ACCESS  read-only
    STATUS  current
    DESCRIPTION
        "The destination IP address of the ARP entry."
    ::= { arpInfoEntry 1 }

arpInfoMacAddr OBJECT-TYPE
    SYNTAX  PhysAddress
    MAX-ACCESS  read-only
    STATUS  current
    DESCRIPTION
        "The MAC address for the ARP entry."
    ::= { arpInfoEntry 2 }

arpInfoVLAN OBJECT-TYPE
    SYNTAX  Integer32
    MAX-ACCESS  read-only
    STATUS  current
    DESCRIPTION
        "The VLAN identifier for the ARP entry."
    ::= { arpInfoEntry 3 }

arpInfoSrcPort OBJECT-TYPE
    SYNTAX  Integer32
    MAX-ACCESS  read-only
    STATUS  current
    DESCRIPTION
        "The  port number on which this entry's equivalence is effective."
    ::= { arpInfoEntry 4 }

arpInfoRefPorts OBJECT-TYPE
    SYNTAX  Integer32
    MAX-ACCESS  read-only
    STATUS  current
    DESCRIPTION
        "The reference SPs associated with this ARP entry."
    ::= { arpInfoEntry 5 }

arpInfoFlag OBJECT-TYPE
    SYNTAX  INTEGER {
	clear(1),
	unresolved(2),
	permanent(3),
	indirect(4),
	layer4(5)
	}
    MAX-ACCESS  read-only
    STATUS  current
    DESCRIPTION
        "The flag associated with this ARP entry."
    ::= { arpInfoEntry 6 }

arpCacheClear OBJECT-TYPE
    SYNTAX  INTEGER {
        ok(1),
        clear(2)
        }
    MAX-ACCESS  read-write
    STATUS  current
    DESCRIPTION
        "Setting this value to clear(2) clears the ARP cache."
    ::= { arpInfo 2 }

-- VRRP Information

vrrpInfoVirtRtrTable OBJECT-TYPE
    SYNTAX  SEQUENCE OF VrrpInfoVirtRtrTableEntry
    MAX-ACCESS  not-accessible
    STATUS  current
    DESCRIPTION
        "The table of VRRP virtual router run-time information."
    ::= { vrrpInfo 1 }

vrrpInfoVirtRtrTableEntry OBJECT-TYPE
    SYNTAX  VrrpInfoVirtRtrTableEntry
    MAX-ACCESS  not-accessible
    STATUS  current
    DESCRIPTION
        "The run-time information about a VRRP virtual router."
    INDEX   { vrrpInfoVirtRtrIndex }
    ::= { vrrpInfoVirtRtrTable 1 }

VrrpInfoVirtRtrTableEntry ::= SEQUENCE {
    vrrpInfoVirtRtrIndex      Integer32,
    vrrpInfoVirtRtrState      INTEGER,
    vrrpInfoVirtRtrOwnership  INTEGER,
    vrrpInfoVirtRtrServer     INTEGER,
    vrrpInfoVirtRtrProxy      INTEGER,
    vrrpInfoVirtRtrPriority   Integer32
    }

vrrpInfoVirtRtrIndex OBJECT-TYPE
    SYNTAX  Integer32
    MAX-ACCESS  read-only
    STATUS  current
    DESCRIPTION
        "The VRRP virtual router index."
    ::= { vrrpInfoVirtRtrTableEntry 1 }

vrrpInfoVirtRtrState OBJECT-TYPE
    SYNTAX  INTEGER {
	init(1),
	master(2),
	backup(3),
	holdoff(4)
	}
    MAX-ACCESS  read-only
    STATUS  current
    DESCRIPTION
        "The VRRP virtual router state."
    ::= { vrrpInfoVirtRtrTableEntry 2 }

vrrpInfoVirtRtrOwnership OBJECT-TYPE
    SYNTAX  INTEGER {
	owner(1),
	renter(2)
	}
    MAX-ACCESS  read-only
    STATUS  current
    DESCRIPTION
        "The VRRP virtual router ownership status."
    ::= { vrrpInfoVirtRtrTableEntry 3 }

vrrpInfoVirtRtrServer OBJECT-TYPE
    SYNTAX  INTEGER {
	yes(1),
	no(2)
	}
    MAX-ACCESS  read-only
    STATUS  current
    DESCRIPTION
        "The VRRP server state identifies virtual routers that support
         Layer 4 services."
    ::= { vrrpInfoVirtRtrTableEntry 4 }

vrrpInfoVirtRtrProxy OBJECT-TYPE
    SYNTAX  INTEGER {
	yes(1),
	no(2)
	}
    MAX-ACCESS  read-only
    STATUS  current
    DESCRIPTION
        "The VRRP proxy state identifies virtual proxy routers."
    ::= { vrrpInfoVirtRtrTableEntry 5 }

vrrpInfoVirtRtrPriority OBJECT-TYPE
    SYNTAX  Integer32
    MAX-ACCESS  read-only
    STATUS  current
    DESCRIPTION
        "The VRRP virtual router priority."
    ::= { vrrpInfoVirtRtrTableEntry 6 }

-- Ospf Information

ospfGeneralInfo  OBJECT IDENTIFIER ::= { ospfinfo 1 }

ospfStartTime OBJECT-TYPE
    SYNTAX  Integer32
    MAX-ACCESS  read-only
    STATUS  current
    DESCRIPTION
        "The time when ospf has been started."
    ::= { ospfGeneralInfo 1 }

ospfProcessUptime OBJECT-TYPE
    SYNTAX  Counter32
    MAX-ACCESS  read-only
    STATUS  current
    DESCRIPTION
        "The time since ospf has been started."
    ::= { ospfGeneralInfo 2 }

ospfLsTypesSupported OBJECT-TYPE
    SYNTAX  Integer32
    MAX-ACCESS  read-only
    STATUS  current
    DESCRIPTION
        "The Link State Types that are supported."
    ::= { ospfGeneralInfo 3 }

ospfIntfCountForRouter OBJECT-TYPE
    SYNTAX  Integer32
    MAX-ACCESS  read-only
    STATUS  current
    DESCRIPTION
        "The number of interfaces for this router."
    ::= { ospfGeneralInfo 4 }

ospfVlinkCountForRouter OBJECT-TYPE
    SYNTAX  Integer32
    MAX-ACCESS  read-only
    STATUS  current
    DESCRIPTION
        "The number of virtual links for this router."
    ::= { ospfGeneralInfo 5 }

ospfTotalNeighbours OBJECT-TYPE
    SYNTAX  Integer32
    MAX-ACCESS  read-only
    STATUS  current
    DESCRIPTION
        "The total number of OSPF neighbours."
    ::= { ospfGeneralInfo 6 }

ospfNbrInInitState OBJECT-TYPE
    SYNTAX  Integer32
    MAX-ACCESS  read-only
    STATUS  current
    DESCRIPTION
        "The number of neighbours in the initial state of exchange."
    ::= { ospfGeneralInfo 7 }

ospfNbrInExchState OBJECT-TYPE
    SYNTAX  Integer32
    MAX-ACCESS  read-only
    STATUS  current
    DESCRIPTION
        "The number of neighbours in the exchange state."
    ::= { ospfGeneralInfo 8 }

ospfNbrInFullState OBJECT-TYPE
    SYNTAX  Integer32
    MAX-ACCESS  read-only
    STATUS  current
    DESCRIPTION
        "The number of neighbours in the Full state of exchange."
    ::= { ospfGeneralInfo 9 }

ospfTotalAreas OBJECT-TYPE
    SYNTAX  Integer32
    MAX-ACCESS  read-only
    STATUS  current
    DESCRIPTION
        "The Total number of areas."
    ::= { ospfGeneralInfo 10 }

ospfTotalTransitAreas OBJECT-TYPE
    SYNTAX  Integer32
    MAX-ACCESS  read-only
    STATUS  current
    DESCRIPTION
        "The Total number of Transit areas."
    ::= { ospfGeneralInfo 11 }

ospfTotalNssaAreas OBJECT-TYPE
    SYNTAX  Integer32
    MAX-ACCESS  read-only
    STATUS  current
    DESCRIPTION
        "The Total number of NSSA areas."
    ::= { ospfGeneralInfo 12 }

ospfAreaInfoTable OBJECT-TYPE
    SYNTAX SEQUENCE OF OspfAreaInfoEntry
    MAX-ACCESS not-accessible
    STATUS current
    DESCRIPTION
      "The table of OSPF Area information."
    ::= { ospfinfo 2 }

ospfAreaInfoEntry OBJECT-TYPE
    SYNTAX OspfAreaInfoEntry
    MAX-ACCESS not-accessible
    STATUS current
    DESCRIPTION
      "Information about a OSPF area."
    INDEX { ospfAreaInfoIndex }
    ::= { ospfAreaInfoTable 1 }

OspfAreaInfoEntry ::= SEQUENCE {
    ospfAreaInfoIndex             Integer32,
    ospfTotalNumberOfInterfaces   Integer32,
    ospfNumberOfInterfacesUp   	  Integer32,
    ospfNumberOfLsdbEntries   	  Integer32,
    ospfAreaInfoId   	          IpAddress

    }

ospfAreaInfoIndex OBJECT-TYPE
    SYNTAX Integer32
    MAX-ACCESS read-only
    STATUS current
    DESCRIPTION
	"The OSPF area number for which the OSPF info table is related."
    ::= { ospfAreaInfoEntry 1}

ospfTotalNumberOfInterfaces OBJECT-TYPE
    SYNTAX Integer32
    MAX-ACCESS read-only
    STATUS current
    DESCRIPTION
	"The total number of interfaces for this OSPF area."
    ::= { ospfAreaInfoEntry 2}

ospfNumberOfInterfacesUp OBJECT-TYPE
    SYNTAX Integer32
    MAX-ACCESS read-only
    STATUS current
    DESCRIPTION
	"The number of interfaces UP in area."
    ::= { ospfAreaInfoEntry 3}

ospfNumberOfLsdbEntries OBJECT-TYPE
    SYNTAX Integer32
    MAX-ACCESS read-only
    STATUS current
    DESCRIPTION
	"The number of Link State Database entries for this OSPF area."
    ::= { ospfAreaInfoEntry 4}

ospfAreaInfoId OBJECT-TYPE
    SYNTAX IpAddress
    MAX-ACCESS read-only
    STATUS current
    DESCRIPTION
	"The IP address of the OSPF area."
    ::= { ospfAreaInfoEntry 5}

ospfIntfInfoTable OBJECT-TYPE
    SYNTAX SEQUENCE OF OspfIntfInfoEntry
    MAX-ACCESS not-accessible
    STATUS current
    DESCRIPTION
      "The table of OSPF Interface information."
    ::= { ospfinfo 3 }

ospfIntfInfoEntry OBJECT-TYPE
    SYNTAX OspfIntfInfoEntry
    MAX-ACCESS not-accessible
    STATUS current
    DESCRIPTION
      "Information about a OSPF interface."
    INDEX { ospfIfInfoIndex }
    ::= { ospfIntfInfoTable 1 }

OspfIntfInfoEntry ::= SEQUENCE {
    ospfIfInfoIndex               	Integer32,
    ospfIfDesignatedRouterIP   	  	IpAddress,
    ospfIfBackupDesignatedRouterIP  	IpAddress,
    ospfIfWaitInterval   	        Integer32,
    ospfIfTotalNeighbours   	  	Integer32,
    ospfIfInfoIpAddress   	  	IpAddress
    }

ospfIfInfoIndex OBJECT-TYPE
    SYNTAX Integer32
    MAX-ACCESS read-only
    STATUS current
    DESCRIPTION
	"The OSPF interface number for which the OSPF info table is related."
    ::= { ospfIntfInfoEntry 1}

ospfIfDesignatedRouterIP OBJECT-TYPE
    SYNTAX IpAddress
    MAX-ACCESS read-only
    STATUS current
    DESCRIPTION
	"The OSPF Designated Router ID (IP Address) for this OSPF interface."
    ::= { ospfIntfInfoEntry 2}

ospfIfBackupDesignatedRouterIP OBJECT-TYPE
    SYNTAX IpAddress
    MAX-ACCESS read-only
    STATUS current
    DESCRIPTION
	"The OSPF Backup Designated Router ID (IP Address) for this OSPF
         interface."
    ::= { ospfIntfInfoEntry 3}

ospfIfWaitInterval OBJECT-TYPE
    SYNTAX Integer32
    MAX-ACCESS read-only
    STATUS current
    DESCRIPTION
	"The OSPF Wait interval for this OSPF interface."
    ::= { ospfIntfInfoEntry 4}

ospfIfTotalNeighbours OBJECT-TYPE
    SYNTAX Integer32
    MAX-ACCESS read-only
    STATUS current
    DESCRIPTION
	"The Total number of neighbours for this OSPF interface."
    ::= { ospfIntfInfoEntry 5}

ospfIfInfoIpAddress OBJECT-TYPE
    SYNTAX IpAddress
    MAX-ACCESS read-only
    STATUS current
    DESCRIPTION
	"The IP address of the OSPF interface."
    ::= { ospfIntfInfoEntry 6}

-- OSPF Interface/Nbr Info Table

ospfIfNbrTable OBJECT-TYPE
    SYNTAX SEQUENCE OF OspfIfNbrEntry
    MAX-ACCESS not-accessible
    STATUS current
    DESCRIPTION
      "The table of OSPF Interface Neighbour information."
    ::= { ospfinfo 5 }

ospfIfNbrEntry OBJECT-TYPE
    SYNTAX OspfIfNbrEntry
    MAX-ACCESS not-accessible
    STATUS current
    DESCRIPTION
      "Information about a OSPF interface, neighbour pair."
    INDEX { ospfIfNbrIntfIndex, ospfIfNbrIpAddr }
    ::= { ospfIfNbrTable 1 }

OspfIfNbrEntry ::= SEQUENCE {
    ospfIfNbrIntfIndex               Integer32,
    ospfIfNbrIpAddr                  IpAddress,
    ospfIfNbrPriority                Integer32,
    ospfIfNbrState                   INTEGER,
    ospfIfNbrDesignatedRtr     	     IpAddress,
    ospfIfNbrBackupDesignatedRtr     IpAddress,
    ospfIfNbrIpAddress               IpAddress
    }

ospfIfNbrIntfIndex OBJECT-TYPE
    SYNTAX Integer32
    MAX-ACCESS read-only
    STATUS current
    DESCRIPTION
	"The OSPF Interface number for which this Interface/Nbr table is
         related."
    ::= { ospfIfNbrEntry 1}

ospfIfNbrIpAddr OBJECT-TYPE
    SYNTAX IpAddress
    MAX-ACCESS read-only
    STATUS current
    DESCRIPTION
	"The OSPF Neighbour ID ."
    ::= { ospfIfNbrEntry 2 }

ospfIfNbrPriority OBJECT-TYPE
    SYNTAX Integer32
    MAX-ACCESS read-only
    STATUS current
    DESCRIPTION
	"The priority of the OSPF neighbour."
    ::= { ospfIfNbrEntry 3 }

ospfIfNbrState OBJECT-TYPE
    SYNTAX  INTEGER {
	down(1),
	attempt(2),
	init(3),
	twoway(4),
	exStart(5),
	exchange(6),
	loading(7),
	full(8)
	}
    MAX-ACCESS read-only
    STATUS current
    DESCRIPTION
	"The state of the OSPF neighbour."
    ::= { ospfIfNbrEntry 4 }

ospfIfNbrDesignatedRtr OBJECT-TYPE
    SYNTAX IpAddress
    MAX-ACCESS read-only
    STATUS current
    DESCRIPTION
	"The IP Address of the Designated Router for this OSPF Neighbour."
    ::= { ospfIfNbrEntry 5 }

ospfIfNbrBackupDesignatedRtr OBJECT-TYPE
    SYNTAX IpAddress
    MAX-ACCESS read-only
    STATUS current
    DESCRIPTION
	"The IP Address of the backup designated Router for this OSPF Neighbour."
    ::= { ospfIfNbrEntry 6 }

ospfIfNbrIpAddress OBJECT-TYPE
    SYNTAX IpAddress
    MAX-ACCESS read-only
    STATUS current
    DESCRIPTION
	"The IP Address of the OSPF Neighbour."
    ::= { ospfIfNbrEntry 7 }

-- Gateway Information
gatewayInfoTable OBJECT-TYPE
    SYNTAX  SEQUENCE OF GatewayInfoEntry
    MAX-ACCESS  not-accessible
    STATUS  current
    DESCRIPTION
        "The table containing information for the default gateways."
    ::= { gatewayInfo 1 }

gatewayInfoEntry OBJECT-TYPE
    SYNTAX  GatewayInfoEntry
    MAX-ACCESS  not-accessible
    STATUS  current
    DESCRIPTION
        "A row in the gateway information table"
    INDEX   { gatewayInfoIndex }
    ::= { gatewayInfoTable 1 }

GatewayInfoEntry ::= SEQUENCE {
    gatewayInfoIndex         Integer32,
    gatewayInfoAddr          IpAddress,
    gatewayInfoVlan          Integer32,
    gatewayInfoAddr6         DisplayString,
    gatewayInfoStatus        INTEGER
    }

gatewayInfoIndex OBJECT-TYPE
    SYNTAX  Integer32
    MAX-ACCESS  read-only
    STATUS  current
    DESCRIPTION
        "The gateway number for which the information is related."
    ::= { gatewayInfoEntry 1}

gatewayInfoAddr OBJECT-TYPE
    SYNTAX  IpAddress
    MAX-ACCESS  read-only
    STATUS  current
    DESCRIPTION
        "The IP address of the default gateway."
    ::= { gatewayInfoEntry 2 }

gatewayInfoVlan OBJECT-TYPE
    SYNTAX  Integer32
    MAX-ACCESS  read-only
    STATUS  current
    DESCRIPTION
        "The VLAN number for this gateway."
    ::= { gatewayInfoEntry 3 }

gatewayInfoStatus OBJECT-TYPE
    SYNTAX  INTEGER {
        up(1),
        failed(2)
	}
    MAX-ACCESS  read-only
    STATUS  current
    DESCRIPTION
        "The status of the default gateway."
    ::= { gatewayInfoEntry 4 }


gatewayInfoAddr6 OBJECT-TYPE
    SYNTAX  DisplayString
    MAX-ACCESS  read-only
    STATUS  current
    DESCRIPTION
        "The IP6 address of the default gateway."
    ::= { gatewayInfoEntry 5 }



-- nbrcache Info Table

nbrcacheInfoTable OBJECT-TYPE
    SYNTAX SEQUENCE OF NbrcacheInfoEntry
    MAX-ACCESS not-accessible
    STATUS current
    DESCRIPTION
        "The table of nbrcache information."
    ::= { nbrcacheInfo 1 }

nbrcacheInfoEntry OBJECT-TYPE
    SYNTAX NbrcacheInfoEntry
    MAX-ACCESS not-accessible
    STATUS current
    DESCRIPTION
        "Information about neighbour discovery protocol."
    INDEX { nbrcacheInfoIndex }
    ::= { nbrcacheInfoTable 1 }

NbrcacheInfoEntry ::= SEQUENCE {
    nbrcacheInfoIndex         Integer32,
    nbrcacheInfoDestIp        DisplayString,
    nbrcacheInfoState         INTEGER,
    nbrcacheInfoType          INTEGER,
    nbrcacheInfoMacAddr       PhysAddress,
    nbrcacheInfoVlanId        Integer32,
    nbrcacheInfoPortNum       Integer32
    }

nbrcacheInfoIndex  OBJECT-TYPE
    SYNTAX  Integer32
    MAX-ACCESS  read-only
    STATUS  current
    DESCRIPTION
        "The index of the nbrcache entry."
    ::= { nbrcacheInfoEntry 1 }

nbrcacheInfoDestIp OBJECT-TYPE
    SYNTAX   DisplayString
    MAX-ACCESS  read-only
    STATUS  current
    DESCRIPTION
        "The destination IP address of the nbrcache entry."
    ::= { nbrcacheInfoEntry 2 }

nbrcacheInfoState  OBJECT-TYPE
    SYNTAX  INTEGER  {
        undef(1),
        reach(2),
        stale(3),
        delay(4),
        probe(5),
        inval(6),
        unknown(7),
        incmp(8)
    }
    MAX-ACCESS  read-only
    STATUS  current
    DESCRIPTION
        "The state of the nbrcache entry."
    ::= { nbrcacheInfoEntry 3 }

nbrcacheInfoType  OBJECT-TYPE
    SYNTAX  INTEGER {
        undef(1),
        other(2),
        invalid(3),
        dynamic(4),
        static(5),
        local(6)
    }
    MAX-ACCESS  read-only
    STATUS  current
    DESCRIPTION
        "The type of the nbrcache entry."
    ::= { nbrcacheInfoEntry 4 }

nbrcacheInfoMacAddr OBJECT-TYPE
    SYNTAX  PhysAddress
    MAX-ACCESS  read-only
    STATUS  current
    DESCRIPTION
        "The MAC address for the nbrcache entry."
    ::= { nbrcacheInfoEntry 5 }

nbrcacheInfoVlanId  OBJECT-TYPE
    SYNTAX  Integer32
    MAX-ACCESS  read-only
    STATUS  current
    DESCRIPTION
        "The VLAN identifier for the nbrcache entry."
    ::= { nbrcacheInfoEntry 6 }

nbrcacheInfoPortNum   OBJECT-TYPE
    SYNTAX  Integer32
    MAX-ACCESS  read-only
    STATUS  current
    DESCRIPTION
        "The  port number on which this entry's equivalence is effective."
    ::= { nbrcacheInfoEntry 7 }

nbrcacheClear OBJECT-TYPE
    SYNTAX  INTEGER {
        ok(1),
        clear(2)
        }
    MAX-ACCESS  read-write
    STATUS  current
    DESCRIPTION
        "Setting this value to clear(2) clears the Nbr cache,
         When read ok(1) is  returned."
    ::= { nbrcacheInfo 2 }

nbrcacheInfoTotDynamicEntries OBJECT-TYPE
    SYNTAX  Integer32
    MAX-ACCESS  read-only
    STATUS  current
    DESCRIPTION
        "The total number of dynamic neighbour cache entries."
    ::= { nbrcacheInfo 3 }

nbrcacheInfoTotLocalEntries OBJECT-TYPE
    SYNTAX  Integer32
    MAX-ACCESS  read-only
    STATUS  current
    DESCRIPTION
        "The total number of local neighbour cache entries."
    ::= { nbrcacheInfo 4 }

nbrcacheInfoTotOtherEntries  OBJECT-TYPE
    SYNTAX  Integer32
    MAX-ACCESS  read-only
    STATUS  current
    DESCRIPTION
        "The total number of other neighbour cache entries."
    ::= { nbrcacheInfo 5 }

ipRoute6InfoTable OBJECT-TYPE
    SYNTAX  SEQUENCE OF IpRoute6InfoEntry
    MAX-ACCESS  not-accessible
    STATUS  current
    DESCRIPTION
        "The table of run-time IP6 routes."
    ::= { ipRoute6Info 1 }

ipRoute6InfoEntry OBJECT-TYPE
    SYNTAX  IpRoute6InfoEntry
    MAX-ACCESS  not-accessible
    STATUS  current
    DESCRIPTION
        "A row in the run-time IP6 route table."
    INDEX   { ipRoute6InfoIndx }
    ::= { ipRoute6InfoTable 1 }

IpRoute6InfoEntry ::= SEQUENCE {
    ipRoute6InfoIndx            Integer32,
    ipRoute6InfoDestIp6         DisplayString,
    ipRoute6InfoInterface       Integer32,
    ipRoute6InfoNextHop         DisplayString,
    ipRoute6InfoProto           INTEGER
    }

ipRoute6InfoIndx OBJECT-TYPE
    SYNTAX  Integer32
    MAX-ACCESS  read-only
    STATUS  current
    DESCRIPTION
        "The index of this route6 table."
    ::= { ipRoute6InfoEntry 1 }

ipRoute6InfoDestIp6 OBJECT-TYPE
    SYNTAX  DisplayString
    MAX-ACCESS  read-only
    STATUS  current
    DESCRIPTION
        "The destination of the route."
    ::= { ipRoute6InfoEntry 2 }

ipRoute6InfoInterface OBJECT-TYPE
    SYNTAX  Integer32
    MAX-ACCESS  read-only
    STATUS  current
    DESCRIPTION
        "The interface of the route."
    ::= { ipRoute6InfoEntry 3 }

ipRoute6InfoNextHop  OBJECT-TYPE
    SYNTAX  DisplayString
    MAX-ACCESS  read-only
    STATUS  current
    DESCRIPTION
        "The next hop of the route."
    ::= { ipRoute6InfoEntry 4 }

ipRoute6InfoProto  OBJECT-TYPE
    SYNTAX  INTEGER {
        isis(1),
        rip(2),
        ospf(3),
        static(4),
        local(5),
        bgp(6),
        stlow(7),
        ospfi(8),
        ospfe(9),
        ospfe2(10),
        ospfa(11),
        ripa(12),
        bgpa(13),
        igmp(14),
        unknown(15),
        natpt(16)
        }
    MAX-ACCESS  read-only
    STATUS  current
    DESCRIPTION
        "The protocol type of the route."
    ::= { ipRoute6InfoEntry 5 }



rip2GeneralInfo	OBJECT IDENTIFIER ::= { rip2Info 1 }

ripInfoState OBJECT-TYPE
    SYNTAX INTEGER {
        on(1),
        off(2)
        }
    MAX-ACCESS read-only
    STATUS current
    DESCRIPTION
	"RIP global state."
    ::= { rip2GeneralInfo 1 }

ripInfoUpdatePeriod OBJECT-TYPE
    SYNTAX  INTEGER  (1..120)
    MAX-ACCESS  read-only
    STATUS  current
    DESCRIPTION
        "Update Period in seconds."
    ::= { rip2GeneralInfo 2 }

ripInfoVip OBJECT-TYPE
    SYNTAX  INTEGER {
        enabled(2),
        disabled(3)
        }
    MAX-ACCESS  read-only
    STATUS  current
    DESCRIPTION
        "Advertise VIP Host Routes."
    ::= { rip2GeneralInfo 3 }

ripInfoStaticSupply OBJECT-TYPE
    SYNTAX  INTEGER {
        enabled(2),
        disabled(3)
        }
    MAX-ACCESS  read-only
    STATUS  current
    DESCRIPTION
        "Advertise Static Routes."
    ::= { rip2GeneralInfo 4 }

rip2InfoIntfTable OBJECT-TYPE
    SYNTAX SEQUENCE OF RipInfoIntfEntry
    MAX-ACCESS not-accessible
    STATUS current
    DESCRIPTION
      "The information table of RIP."
    ::= { rip2Info 2 }

ripInfoIntfEntry OBJECT-TYPE
    SYNTAX RipInfoIntfEntry
    MAX-ACCESS not-accessible
    STATUS current
    DESCRIPTION
      "Information about  RIP on IP interface."
    INDEX { ripInfoIntfIndex }
    ::= { rip2InfoIntfTable 1 }

RipInfoIntfEntry ::= SEQUENCE {
    ripInfoIntfIndex  	      Integer32,
    ripInfoIntfVersion	      INTEGER,
    ripInfoIntfAddress        IpAddress,
    ripInfoIntfState	      INTEGER,
    ripInfoIntfListen	      INTEGER,
    ripInfoIntfTrigUpdate     INTEGER,
    ripInfoIntfMcastUpdate    INTEGER,
    ripInfoIntfPoisonReverse  INTEGER,
    ripInfoIntfSupply         INTEGER,
    ripInfoIntfMetric         INTEGER,
    ripInfoIntfAuth           INTEGER,
    ripInfoIntfKey            DisplayString,
    ripInfoIntfDefault	      INTEGER
    }

ripInfoIntfIndex OBJECT-TYPE
    SYNTAX Integer32
    MAX-ACCESS read-only
    STATUS current
    DESCRIPTION
	"The interface number for which the RIP information is related."
    ::= { ripInfoIntfEntry 1 }

ripInfoIntfVersion OBJECT-TYPE
    SYNTAX INTEGER {
        ripVersion1(1),
        ripVersion2(2)
        }
    MAX-ACCESS read-only
    STATUS current
    DESCRIPTION
        "RIP version."
    ::= { ripInfoIntfEntry 2 }

ripInfoIntfAddress OBJECT-TYPE
    SYNTAX  IpAddress
    MAX-ACCESS read-only
    STATUS current
    DESCRIPTION
        "The interface address."
    ::= { ripInfoIntfEntry 3 }

ripInfoIntfState OBJECT-TYPE
    SYNTAX INTEGER {
        enabled(1),
        disabled(2)
        }
    MAX-ACCESS read-only
    STATUS current
    DESCRIPTION
        "The status of RIP protocol."
    ::= { ripInfoIntfEntry 4 }

ripInfoIntfListen OBJECT-TYPE
    SYNTAX INTEGER {
        enabled(1),
        disabled(2)
        }
    MAX-ACCESS read-only
    STATUS current
    DESCRIPTION
        "The status of listening to route updates."
    ::= { ripInfoIntfEntry 5 }

ripInfoIntfTrigUpdate OBJECT-TYPE
    SYNTAX INTEGER {
        enabled(1),
        disabled(2)
        }
    MAX-ACCESS read-only
    STATUS current
    DESCRIPTION
	"The status of triggered updates."
    ::= { ripInfoIntfEntry 6 }

ripInfoIntfMcastUpdate OBJECT-TYPE
    SYNTAX INTEGER {
        enabled(1),
        disabled(2)
        }
    MAX-ACCESS read-only
    STATUS current
    DESCRIPTION
	"The status of multicast updates."
    ::= { ripInfoIntfEntry 7 }

ripInfoIntfPoisonReverse OBJECT-TYPE
    SYNTAX  INTEGER {
        enabled(1),
        disabled(2)
        }
    MAX-ACCESS read-only
    STATUS current
    DESCRIPTION
	"The status of RIP poison reverse."
    ::= { ripInfoIntfEntry 8 }

ripInfoIntfSupply OBJECT-TYPE
    SYNTAX INTEGER {
        enabled(1),
        disabled(2)
        }
    MAX-ACCESS read-only
    STATUS current
    DESCRIPTION
        "The status of supplying route updates."
    ::= { ripInfoIntfEntry 9 }

ripInfoIntfMetric OBJECT-TYPE
    SYNTAX  INTEGER (1..15)
    MAX-ACCESS read-only
    STATUS current
    DESCRIPTION
        "RIP route metric for this interface."
    ::= { ripInfoIntfEntry 10 }

ripInfoIntfAuth OBJECT-TYPE
    SYNTAX INTEGER {
        none(1),
        password(2)
        }
    MAX-ACCESS read-only
    STATUS current
    DESCRIPTION
        "The type of Authentication used on this interface."
    ::= { ripInfoIntfEntry 11 }

ripInfoIntfKey OBJECT-TYPE
    SYNTAX  DisplayString (SIZE(0..16))
    MAX-ACCESS  read-only
    STATUS  current
    DESCRIPTION
        "RIP update authentication password."
    ::= { ripInfoIntfEntry 12 }

ripInfoIntfDefault OBJECT-TYPE
    SYNTAX  INTEGER {
        both(1),
        listen(2),
        supply(3),
        none(4)
        }
    MAX-ACCESS read-only
    STATUS current
    DESCRIPTION
	"Specifies what RIP does with default routes."
    ::= { ripInfoIntfEntry 13 }


rip2RoutesInfoTable OBJECT-TYPE
    SYNTAX SEQUENCE OF Rip2RoutesInfoEntry
    MAX-ACCESS not-accessible
    STATUS current
    DESCRIPTION
        "The table of rip routes."
    ::= { rip2RoutesInfo 1 }

rip2RoutesInfoEntry OBJECT-TYPE
    SYNTAX Rip2RoutesInfoEntry
    MAX-ACCESS not-accessible
    STATUS current
    DESCRIPTION
        "Information about rip routes."
    INDEX { rip2RoutesInfoDestIndex, rip2RoutesInfoNxtHopIndex }
    ::= { rip2RoutesInfoTable 1 }

Rip2RoutesInfoEntry ::= SEQUENCE {
    rip2RoutesInfoDestIndex     Integer32,
    rip2RoutesInfoNxtHopIndex   Integer32,
    rip2RoutesInfoDestination   DisplayString,
    rip2RoutesInfoIpAddress     IpAddress,
    rip2RoutesInfoMetric        INTEGER
    }

rip2RoutesInfoDestIndex  OBJECT-TYPE
    SYNTAX  Integer32
    MAX-ACCESS  read-only
    STATUS  current
    DESCRIPTION
        "The index of the rip routes."
    ::= { rip2RoutesInfoEntry 1 }

rip2RoutesInfoNxtHopIndex  OBJECT-TYPE
    SYNTAX  Integer32
    MAX-ACCESS  read-only
    STATUS  current
    DESCRIPTION
        "The index of the next hop."
    ::= { rip2RoutesInfoEntry 2 }

rip2RoutesInfoDestination  OBJECT-TYPE
    SYNTAX   DisplayString
    MAX-ACCESS  read-only
    STATUS  current
    DESCRIPTION
        "The destination of the rip route."
    ::= { rip2RoutesInfoEntry 3 }

rip2RoutesInfoIpAddress  OBJECT-TYPE
    SYNTAX  IpAddress
    MAX-ACCESS  read-only
    STATUS  current
    DESCRIPTION
        "The ipaddress of the next hop."
    ::= { rip2RoutesInfoEntry  4 }

rip2RoutesInfoMetric  OBJECT-TYPE
    SYNTAX   INTEGER ( 1..15 )
    MAX-ACCESS  read-only
    STATUS  current
    DESCRIPTION
        "RIP route metric for this route."
    ::= { rip2RoutesInfoEntry  5 }

allowedNwInfoTable OBJECT-TYPE
    SYNTAX  SEQUENCE OF AllowedNwInfoEntry
    MAX-ACCESS  not-accessible
    STATUS  current
    DESCRIPTION
        "The table of allowed network run-time information."
    ::= { allowedNwInfo 1 }

allowedNwInfoEntry OBJECT-TYPE
    SYNTAX  AllowedNwInfoEntry
    MAX-ACCESS  not-accessible
    STATUS  current
    DESCRIPTION
        "A row in the allowed network information table."
    INDEX   { allowedNwInfoIndex }
    ::= { allowedNwInfoTable 1 }

AllowedNwInfoEntry ::= SEQUENCE {
    allowedNwInfoIndex           Integer32,
    allowedNwInfoIpver           INTEGER,
    allowedNwInfoVlan            Integer32,
    allowedNwInfoBeginIpAddr     DisplayString,
    allowedNwInfoEndIpAddr       DisplayString,
    allowedNwInfoNetMask         DisplayString,
    allowedNwInfoIp6Prefix       Integer32
    }

allowedNwInfoIndex OBJECT-TYPE
    SYNTAX  Integer32
    MAX-ACCESS  read-only
    STATUS  current
    DESCRIPTION
        "The allowed network index"
    ::= { allowedNwInfoEntry 1 }

allowedNwInfoIpver  OBJECT-TYPE
    SYNTAX   INTEGER {
        ipv4(1),
        ipv6(2)
        }
    MAX-ACCESS  read-only
    STATUS  current
    DESCRIPTION
        "The type of IP address."
    ::= { allowedNwInfoEntry 2 }

allowedNwInfoVlan OBJECT-TYPE
    SYNTAX  Integer32
    MAX-ACCESS  read-only
    STATUS  current
    DESCRIPTION
        "The VLAN that the allowed network belongs to."
    ::= { allowedNwInfoEntry 3 }

allowedNwInfoBeginIpAddr  OBJECT-TYPE
    SYNTAX   DisplayString
    MAX-ACCESS  read-only
    STATUS  current
    DESCRIPTION
        "The begin IP address of the allowed network."
    ::= { allowedNwInfoEntry 4 }

allowedNwInfoEndIpAddr  OBJECT-TYPE
    SYNTAX   DisplayString
    MAX-ACCESS  read-only
    STATUS  current
    DESCRIPTION
        "The begin IP address of the allowed network."
    ::= { allowedNwInfoEntry 5 }

allowedNwInfoNetMask OBJECT-TYPE
    SYNTAX   DisplayString
    MAX-ACCESS  read-only
    STATUS  current
    DESCRIPTION
        "The subnet mask of the allowed network."
    ::= { allowedNwInfoEntry 6 }

allowedNwInfoIp6Prefix OBJECT-TYPE
    SYNTAX  Integer32
    MAX-ACCESS  read-only
    STATUS  current
    DESCRIPTION
        "The prefix length of the IP6 allowed network."
    ::= { allowedNwInfoEntry 7 }

-- L3 Operational commands

vrrpOperVirtRtrTable OBJECT-TYPE
    SYNTAX  SEQUENCE OF VrrpOperVirtRtrEntry
    MAX-ACCESS  not-accessible
    STATUS  current
    DESCRIPTION
        "An entry in the table of virtual routers."
    ::= { vrrpOper 1 }

vrrpOperVirtRtrEntry OBJECT-TYPE
    SYNTAX  VrrpOperVirtRtrEntry
    MAX-ACCESS  not-accessible
    STATUS  current
    DESCRIPTION
        "A row in the vrrpOperVirtRtrTable "
    INDEX   { vrrpOperVirtRtrIndex }
    ::= { vrrpOperVirtRtrTable 1 }

VrrpOperVirtRtrEntry ::= SEQUENCE {
    vrrpOperVirtRtrIndex              Integer32,
    vrrpOperVirtRtrBackup             INTEGER
    }

vrrpOperVirtRtrIndex OBJECT-TYPE
    SYNTAX  Integer32
    MAX-ACCESS  read-only
    STATUS  current
    DESCRIPTION
        "The index for the  VRRP virtual router."
    ::= { vrrpOperVirtRtrEntry 1 }

vrrpOperVirtRtrBackup OBJECT-TYPE
    SYNTAX  INTEGER {
	ok(1),
	backup(2)
	}
    MAX-ACCESS  read-write
    STATUS  current
    DESCRIPTION
        "When set to a value of 'backup(2)' it forces the specified
         master virtual router into backup mode.
         'ok(1)' is returned when the object os read."
    ::= { vrrpOperVirtRtrEntry 2 }

vrrpOperVirtRtrGroupBackup OBJECT-TYPE
    SYNTAX  INTEGER {
	ok(1),
	backup(2)
	}
    MAX-ACCESS  read-write
    STATUS  current
    DESCRIPTION
        "When set to a value of 'backup(2)' it forces the specified
         master virtual router group into backup mode.
         'ok(1)' is returned when the object os read."
    ::= { vrrpOper 2 }

bgpOper             OBJECT IDENTIFIER ::= { ipOper 1 }
garpOper            OBJECT IDENTIFIER ::= { ipOper 2 }

bgpOperStart        OBJECT IDENTIFIER ::= { bgpOper 1 }
bgpOperStop         OBJECT IDENTIFIER ::= { bgpOper 2 }

bgpOperStartPeerNum OBJECT-TYPE
    SYNTAX INTEGER (1..16)
    MAX-ACCESS  read-write
    STATUS  current
    DESCRIPTION
      "Enter BGP peer Number.Value 1 is returned when object is read."
    ::= { bgpOperStart 1 }

bgpOperStartSess OBJECT-TYPE
    SYNTAX INTEGER {
        ok(1),
        start(2)
    }
    MAX-ACCESS  read-write
    STATUS  current
    DESCRIPTION
      "This is the action object,start(2) is to Start BGP peer session.
       ok(1) is returned when object is read"
    ::= { bgpOperStart 2 }

bgpOperStopPeerNum OBJECT-TYPE
    SYNTAX INTEGER (1..16)
    MAX-ACCESS  read-write
    STATUS  current
    DESCRIPTION
      "Enter BGP peer Number.Value 1 is returned when object is read."
    ::= { bgpOperStop 1 }

bgpOperStopSess OBJECT-TYPE
    SYNTAX INTEGER {
        ok(1),
        stop(2)
    }
    MAX-ACCESS  read-write
    STATUS  current
    DESCRIPTION
      "This is an action object,stop(2) is to Stop BGP peer session.
       ok(1) is returned when object is read"
    ::= { bgpOperStop 2 }

garpOperIpAddr OBJECT-TYPE
    SYNTAX IpAddress
    MAX-ACCESS  read-write
    STATUS  current
    DESCRIPTION
      "Ip Address to Send gratuitous arp.Value 0.0.0.0 is returned when object is read."
    ::= { garpOper 1 }

garpOperVlanNumber OBJECT-TYPE
    SYNTAX INTEGER (1..4090)
    MAX-ACCESS  read-write
    STATUS  current
    DESCRIPTION
      "Vlan Number to Send gratuitous arp.Value 1 is returned when object is read."
    ::= { garpOper 2 }

garpOperSend OBJECT-TYPE
    SYNTAX INTEGER {
        ok(1),
        send(2),
        error(3)
    }
    MAX-ACCESS  read-write
    STATUS  current
    DESCRIPTION
      "This is an action object,When set to value of send(2),
       it sends gratuitous arp.ok(1) is returned when garp
       request is sent successfully.Otherwise error(3) is returned."
    ::= { garpOper 3 }


END
