SWPRIMGMT-MIB    DEFINITIONS ::= BEGIN

    IMPORTS
        MODULE-IDENTITY             FROM SNMPv2-SMI
        rcMgmt                      FROM RAPID-CITY;


    cobra                OBJECT IDENTIFIER ::= { rcMgmt 201 }
    privateMgmt          OBJECT IDENTIFIER ::= { cobra 1 }

END
