RC-PLSB-MIB DEFINITIONS ::= BEGIN

IMPORTS
    MODULE-IDENTITY, OBJECT-TYPE, Integer32, IpAddress, Counter64, Counter32, Gauge32
        FROM SNMPv2-SMI
    DisplayString, TruthValue, MacAddress, RowStatus, DateAndTime, TimeStamp
        FROM SNMPv2-TC
    InterfaceIndex
        FROM IF-MIB
    rcPlsb, EnableValue
        FROM RAPID-CITY
    IpIsisPlsbNodeNickName
        FROM RC-IP-MIB;

rcPlsbMib MODULE-IDENTITY
       LAST-UPDATED     "202011120000Z"
       ORGANIZATION "Nortel Networks"
       CONTACT-INFO "Marty Lok
             Postal:  Nortel Networks, Inc.
                      600 Technology Park
                      Billerica, MA 01821
              email:  malok@nortel.com
                      "
       DESCRIPTION      "Enterprise MIB for the Accelar product family."

       REVISION "202011120000Z" -- 12 Nov 2020
       DESCRIPTION "Version 13:
                    Update rcPlsbGlobalNicknameServerPrefix description"


       REVISION "202010290000Z" -- 29 Oct 2020
       DESCRIPTION "Version 12:
                    Update  rcPlsbGlobalNicknameServerRange  description"


       REVISION "202010270000Z" -- 27 Oct 2020
       DESCRIPTION "Version 11: added rcPlsbGlobalNicknameServerPrefix
                    Deprecated rcPlsbGlobalNicknameServerRange "


       REVISION "201712190000Z" -- 19 Dec 2017
       DESCRIPTION "Version 10: removed rcPlsbGlobalNicknameMode
	   		  Update rcPlsbGlobalNicknameServerRange
			       rcPlsbGlobalNicknameServerMode"

       REVISION "201706130000Z" -- 13 June 2017
       DESCRIPTION "Version 9: Added rcPlsbGlobalNicknameMode
	   		rcPlsbGlobalNicknameServerRange
			rcPlsbGlobalNicknameServerMode"

       REVISION "201611110000Z" -- 11 November 2016
       DESCRIPTION "Version 8: Added rcPlsbGlobalUcFibHashAlg.
	   		       Submit 29484 (VSP9000) (zuyanwa)"

       REVISION "201601200000Z" -- 20 January 2016
       DESCRIPTION "Version 7: Added rcPlsbGlobalStreamCountTrapEnable.
	   		       Submit 43805 (ERS) (prempa)"

       REVISION "201201200000Z" -- 20 January 2012
       DESCRIPTION "Version 6: Remove rcPlsbGlobalTlvVersion"

       REVISION "201106160000Z" -- 16 June 2011
       DESCRIPTION "Version 5: Added rcPlsbTlvVersion"

       REVISION "201101060000Z" -- 06 January 2011
       DESCRIPTION "Version 4: Added rcPlsbGlobalEtherType"

       REVISION "200907020000Z" -- 07 July 2009
       DESCRIPTION "Version 3: Added     rcPlsbGlobal(3)"

       REVISION "200805270000Z" -- 27 May 2008
       DESCRIPTION "Version 2:  Fixed the IMPORTS syntax porblem"

       REVISION "200804210000Z" -- 21 April 2008
       DESCRIPTION "Version 1: Added     rcPlsbGlobal(1),
                                         rcPlsbGlobal(2)"

       ::= { rcPlsb 0 }


--rcPlsbGlobals

rcPlsbGlobal  OBJECT IDENTIFIER ::= {rcPlsb 1}

rcPlsbGlobalVlans OBJECT-TYPE
   	SYNTAX		OCTET STRING(SIZE(512))
    	MAX-ACCESS	read-write
    	STATUS		current
    	DESCRIPTION	"PLSB vlan entry."
    	::= { rcPlsbGlobal 1}

rcPlsbGlobalEnable OBJECT-TYPE
   	SYNTAX		EnableValue
    	MAX-ACCESS	read-write
    	STATUS		current
    	DESCRIPTION	"Enable/Disable PLSB global flag."
        DEFVAL          {disable}
    	::= { rcPlsbGlobal 2}

rcPlsbGlobalMsti OBJECT-TYPE
        SYNTAX        INTEGER (0..63)
        MAX-ACCESS    read-write
        STATUS        current
        DESCRIPTION   "MSTI instance ID for PLSB VLANS"
	DEFVAL       { 0 }
        ::= { rcPlsbGlobal 3}

rcPlsbGlobalEtherType OBJECT-TYPE
	SYNTAX        Integer32 (1..'FFFF'h)
        MAX-ACCESS    read-write
        STATUS        current
        DESCRIPTION   "SPBM Ethertype"
	DEFVAL        { '8100'h }
	::= { rcPlsbGlobal 4}

rcPlsbGlobalStreamCountTrapEnable OBJECT-TYPE
        SYNTAX          TruthValue
        MAX-ACCESS      read-write
        STATUS          current
        DESCRIPTION     "Enable/Disable PLSB stream count trap flag."
        DEFVAL          { false }
        ::= { rcPlsbGlobal 5 }

rcPlsbGlobalUcFibHashAlg OBJECT-TYPE
        SYNTAX        INTEGER {
                          default(1),
                          correlation(2),
                          random(3)
                      }
        MAX-ACCESS    read-write
        STATUS        current
        DESCRIPTION   "SPBM UC FIB Table Hash Algorithm"
        DEFVAL        { default }
        ::= { rcPlsbGlobal 6}

rcPlsbGlobalNicknameDynamicAllocationStatus OBJECT-TYPE
        SYNTAX       EnableValue
	MAX-ACCESS   read-only
        STATUS       current
        DESCRIPTION "Dynamic Nick-name Allocation service operational status."
        ::= { rcPlsbGlobal 7}

rcPlsbGlobalNicknameServerRange OBJECT-TYPE
        SYNTAX       INTEGER {
			rangeA(10), -- A.00.00 to A.FF.FF --
			rangeB(11), -- B.00.00 to B.FF.FF --
			rangeC(12), -- C.00.00 to C.FF.FF --
			rangeD(13), -- D.00.00 to D.FF.FF --
			rangeE(14), -- E.00.00 to E.FF.FF --
			rangeF(15),  -- F.00.00 to F.FF.FF --
            nonde(255)   -- none --
		     }
	MAX-ACCESS   read-write
	STATUS       current
	DESCRIPTION  "Nick-name Range A-F.xx.xx specifies the range of
	    	      Nick-names that will be dynamically assigned by the
		      SPBM Nick-name Server to requesting clients.
		      This configuration is only used when the SPBM Nick-name
		      Server feature is enabled.  none(255) means the new rcPlsbGlobalNicknameServerPrefix object is in use"
	DEFVAL       { rangeA }
	::= { rcPlsbGlobal 8}

rcPlsbGlobalNicknameServerEnable OBJECT-TYPE
       SYNTAX        EnableValue
       MAX-ACCESS    read-write
       STATUS        current
       DESCRIPTION   "Nick-name Server enabled state (disabled via duplicate detection)."
       DEFVAL { disable }
       ::= { rcPlsbGlobal 9}

rcPlsbGlobalNicknameServerPrefix OBJECT-TYPE
        SYNTAX IpIsisPlsbNodeNickName
        MAX-ACCESS read-write
        STATUS current
        DESCRIPTION   "The prefix is the value of the first octet of the Nick-name. There are 256 possible Nick-name prefixes in total: 0.00.00 - F.F0.00 corresponding to 256 ranges: 0.0x.xx - F.Fx.xx, with 4k Nick-names each. This configuration is only used when the SPBM Nick-name Server feature is enabled. F.FF.FF value means that the rcPlsbGlobalNicknameServerRange object is in use."
        ::= { rcPlsbGlobal 10 }
END
