--[DOC]---------------------------------------------------------------------
--
-- Revision History:
--
----------------------------------------------------------------------------
-- Date		Engineer	Description
-- 05/29/07     lmilitar        Add a sysObjectID value for CES2750
--[ENDDOC]------------------------------------------------------------------
--
        NEWOAK-MIB DEFINITIONS ::= BEGIN

        IMPORTS
                enterprises							FROM RFC1155-SMI
				MODULE-IDENTITY				 		FROM SNMPv2-SMI;

      newoak    OBJECT IDENTIFIER ::= { enterprises 2505 }

-- The following MODULE-IDENTITY definition can be commented out if the MIB parser
-- you are using has trouble parsing it. If you do comment it out, then uncomment
-- the following object identifier defintion.
--    contivity OBJECT IDENTIFIER ::= {newoak 1}
--
	  contivity  MODULE-IDENTITY
			LAST-UPDATED "0004252130Z"  -- April 25, 2000 7:30pm EST
			ORGANIZATION "Nortel"
			CONTACT-INFO
				   "support@nortel.com
            Postal: Nortel
                    600 Technology Park Drive
                    Billerica, MA 01821
            Tel:    +1 978 670 8888
            E-Mail: support@nortel.com"

			DESCRIPTION
				"This MIB defines the sysObjectIDs for different variations
				 of the VPN Router."
			REVISION     "0005122045Z"   -- May 12, 2000 4:45pm EST
			DESCRIPTION
                "Reversed the 1600 and 2600 ids."
			::= { newoak 1 }

-- Wish we could do this BUT, its already taken	  vpnRouter4000 OBJECT IDENTIFIER ::= {newoak 1}
	  vpnRouter2000 OBJECT IDENTIFIER ::= {newoak 2}
	  vpnRouter1000 OBJECT IDENTIFIER ::= {newoak 3}
	  vpnRouter4500 OBJECT IDENTIFIER ::= {newoak 4}
	  vpnRouter15XX OBJECT IDENTIFIER ::= {newoak 5}
	  vpnRouter2500 OBJECT IDENTIFIER ::= {newoak 6}
	  vpnRouter1600 OBJECT IDENTIFIER ::= {newoak 7}
	  vpnRouter2600 OBJECT IDENTIFIER ::= {newoak 8}
	  vpnRouter4600 OBJECT IDENTIFIER ::= {newoak 9}
	  vpnRouter1700 OBJECT IDENTIFIER ::= {newoak 1700}
	  vpnRouter1740 OBJECT IDENTIFIER ::= {newoak 1740}
	  vpnRouter1750 OBJECT IDENTIFIER ::= {newoak 1750}
	  vpnRouter2700 OBJECT IDENTIFIER ::= {newoak 2700}
	  vpnRouter1010 OBJECT IDENTIFIER ::= {newoak 1010}
	  vpnRouter1050 OBJECT IDENTIFIER ::= {newoak 1050}
	  vpnRouter1100 OBJECT IDENTIFIER ::= {newoak 1100}
	  vpnRouter600 OBJECT IDENTIFIER ::= {newoak 600}
	  vpnRouter5000 OBJECT IDENTIFIER ::= {newoak 5000}
	  vpnRouter2750 OBJECT IDENTIFIER ::= {newoak 2750}


      END
